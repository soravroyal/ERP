FME workspace Access2FileGeodatabase.fmw

Parameters:
- DestGDB = $(FME_MF_DIR)lcp_2016v1.gdb   # Destination File Geodatabase
- SorceMDB = $(FME_MF_DIR)LCP_database_v2_1.mdb   # Source Access Database File(s)

Readers:
- MDB_ADO_1: MDB_ADO from $(SorceMDB)

Writers:
- GEODATABASE_FILE_1: GEODATABASE_FILE to $(DestGDB)

1_BasicData (reader MDB_ADO_1)
    attributes: ID autonumber, MemberState text(255), ReferenceYear long, NumberOfPlants long, Organization text(255), Address1 text(255), Address2 text(255), City text(255), State text(255), PostalCode text(255), NameOfContactPerson text(255), Phone text(255), EMail text(255)
    -> AttributeCreator_3
AttributeCreator_3
    ATTR_TABLE:
      SET_TO BasicID = @Value(ID)
      SET_TO OBJECTID = @Value(ID)
    -> BasicData (writer GEODATABASE_FILE_1)
BasicData (writer GEODATABASE_FILE_1)
    attributes: OBJECTID char(200), MemberState char(255), ReferenceYear integer, NumberOfPlants integer, Organization char(255), Address1 char(255), Address2 char(255), City char(255), State char(255), PostalCode char(255), NameOfContactPerson char(255), Phone char(255), EMail char(255), BasicID integer
5_OptOutsAndNERP (reader MDB_ADO_1)
    attributes: ID autonumber, FK_Plant_ID long, Unique_Plant_Id text(255), PlantName text(255), OptOutPlant yesno, CapacityOptedOutMW double, HoursOperated long, PlantIncludedInNERP yesno
    -> AttributeCreator_4
AttributeCreator_4
    ATTR_TABLE = SET_TO OBJECTID = @Value(ID)
    -> OptOutsAndNERP (writer GEODATABASE_FILE_1)
OptOutsAndNERP (writer GEODATABASE_FILE_1)
    attributes: OBJECTID char(200), ID integer, FK_Plant_ID integer, Unique_Plant_Id char(255), PlantName char(255), OptOutPlant boolean, CapacityOptedOutMW double, HoursOperated integer, PlantIncludedInNERP boolean
4_EnergyInputAndTotalEmissionsToAir (reader MDB_ADO_1)
    attributes: ID autonumber, FK_Plant_ID long, Unique_Plant_ID text(255), PlantName text(255), Biomass double, OtherSolidFuels double, LiquidFuels double, NaturalGas double, OtherGases double, SO2 double, NOx double, Dust double
    -> AttributeCreator_5
AttributeCreator_5
    ATTR_TABLE = SET_TO OBJECTID = @Value(ID)
    -> EnergyInputAndTotalEmissionsToAir (writer GEODATABASE_FILE_1)
EnergyInputAndTotalEmissionsToAir (writer GEODATABASE_FILE_1)
    attributes: OBJECTID char(200), ID integer, FK_Plant_ID integer, Unique_Plant_ID char(255), PlantName char(255), Biomass double, OtherSolidFuels double, LiquidFuels double, NaturalGas double, OtherGases double, SO2 double, NOx double, Dust double
6_LcpArt15 (reader MDB_ADO_1)
    attributes: ID autonumber, FK_Plant_ID long, Unique_Plant_ID text(255), PlantName text(255), Art5_1 yesno, OperatingHours long, ElvSO2 double, NotaBeneAnnexIII yesno, NotaBeneElvSO2 double, DesulphurisationRate double, SInput double, AnnexVI_A_Footnote2 yesno, AnnexVI_A_Footnote2_OperatingHours long, ElvNOx double, AnnexVI_A_Footnote3 yesno, VolatileContents double, AnnexVI_A_Footnote3_ElvNOx double, Comments text(255)
    -> AttributeCreator_6
AttributeCreator_6
    ATTR_TABLE = SET_TO OBJECTID = @Value(ID)
    -> LcpArt15 (writer GEODATABASE_FILE_1)
LcpArt15 (writer GEODATABASE_FILE_1)
    attributes: OBJECTID char(200), ID integer, FK_Plant_ID integer, Unique_Plant_ID char(255), PlantName char(255), Art5_1 boolean, OperatingHours integer, ElvSO2 double, NotaBeneAnnexIII boolean, NotaBeneElvSO2 double, DesulphurisationRate double, SInput double, AnnexVI_A_Footnote2 boolean, AnnexVI_A_Footnote2_OperatingHours integer, ElvNOx double, AnnexVI_A_Footnote3 boolean, VolatileContents double, AnnexVI_A_Footnote3_ElvNOx double, Comments char(255)
2_Plant (reader MDB_ADO_1)
    attributes: ID autonumber, FK_BasicData_ID long, Unique_Plant_ID text(255), PlantName text(255), FacilityName text(255), EPRTRNationalId text(255), Address1 text(255), Address2 text(255), City text(255), Region text(255), PostalCode text(255), Longitude text(255), Latitude text(255)
    -> AttributeCreator
AttributeCreator
    ATTR_TABLE:
      SET_TO Longitude = FME_CONDITIONAL:DEFAULT_VALUE'@Evaluate(@Value(Longitude))'BOOL_OP;OR;COMPOSITE_TEST;<Unused>;TEST @Value(Longitude) NOT_TYPE NUM'@Evaluate(0)'FME_NUM_CONDITIONS2___
      SET_TO Latitude = FME_CONDITIONAL:DEFAULT_VALUE'@Evaluate(@Value(Latitude))'BOOL_OP;OR;COMPOSITE_TEST;<Unused>;TEST @Value(Latitude) NOT_TYPE NUM'@Evaluate(0)'FME_NUM_CONDITIONS2___
      SET_TO La
    -> AttributeCreator_2
AttributeCreator_2
    ATTR_TABLE:
      SET_TO OBJECTID = @Value(ID)
      SET_TO PlantID = @Value(ID)
    -> VertexCreator
VertexCreator
    MODE_NAME = Add Point
    YVAL = @Value(Latitude)
    XVAL = @Value(Longitude)
    -> CoordinateSystemSetter
CoordinateSystemSetter
    COORDSYS = EPSG:4326
    -> Reprojector
Reprojector
    SOURCE = Read from feature
    DEST = EPSG:3857
    INTERPOLATION_TYPE_NAME = Nearest Neighbor
    RASTER_CELL_SIZE = Preserve Cells
    REPROJECTED -> Plant_Layer (writer GEODATABASE_FILE_1)
Plant_Layer (writer GEODATABASE_FILE_1)
    attributes: ID char(200), FK_BasicData_ID integer, Unique_Plant_ID char(255), PlantName char(255), FacilityName char(255), EPRTRNationalId char(255), Address1 char(255), Address2 char(255), City char(255), Region char(255), PostalCode char(255), Longitude double, Latitude double, PlantID integer
3_PlantDetails (reader MDB_ADO_1)
    attributes: ID autonumber, FK_Plant_ID long, Unique_Plant_ID text(255), PlantName text(255), StatusOfThePlant text(255), MWth double, ExtensionBy50MWOrMore yesno, CapacityAddedMW double, SubstantialChange yesno, CapacityAffectedMW double, DateOfStartOfOperation text(255), Refineries yesno, OtherSector text(255), GasTurbine yesno, GasTurbineThermalInput double, Boiler yesno, BoilerThermalInput double, GasEngine yesno, GasEngineThermalInput double, DieselEngine yesno, DieselEngineThermalInput double, Other yesno, OtherTypeOfCombustion text(255), OtherThermalInput double, OperatingHours long, Comments text(255)
    -> AttributeCreator_7
AttributeCreator_7
    ATTR_TABLE = SET_TO OBJECTID = @Value(ID)
    -> PlantDetails (writer GEODATABASE_FILE_1)
PlantDetails (writer GEODATABASE_FILE_1)
    attributes: OBJECTID char(200), ID integer, FK_Plant_ID integer, Unique_Plant_ID char(255), PlantName char(255), StatusOfThePlant char(255), MWth double, ExtensionBy50MWOrMore boolean, CapacityAddedMW double, SubstantialChange boolean, CapacityAffectedMW double, DateOfStartOfOperation char(255), Refineries boolean, OtherSector char(255), GasTurbine boolean, GasTurbineThermalInput double, Boiler boolean, BoilerThermalInput double, GasEngine boolean, GasEngineThermalInput double, DieselEngine boolean, DieselEngineThermalInput double, Other boolean, OtherTypeOfCombustion char(255), OtherThermalInput double, OperatingHours integer, Comments char(255)
Overview (reader MDB_ADO_1)
    attributes: MemberState text(255), ReferenceYear long, Unique_Plant_ID text(255), PlantName text(255), MWth double, Biomass double, OtherSolidFuels double, LiquidFuels double, NaturalGas double, OtherGases double, SO2 double, NOx double, Dust double
    -> Overview (writer GEODATABASE_FILE_1)
Overview (writer GEODATABASE_FILE_1) [off]
    attributes: MemberState char(255), ReferenceYear integer, Unique_Plant_ID char(255), PlantName char(255), MWth double, Biomass double, OtherSolidFuels double, LiquidFuels double, NaturalGas double, OtherGases double, SO2 double, NOx double, Dust double
