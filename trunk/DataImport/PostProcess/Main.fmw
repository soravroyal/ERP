FME workspace Main.fmw

Creator
    NUM = 1
    GEOMTYPE = Geometry Object
    CREATED -> WorkspaceRunner
WorkspaceRunner
    WORKSPACE_FILE = $(FME_MF_DIR)accessToCSV.fmw
    WORKSPACE_PARAMETERS = SourceDataset_MDB_ADO,S:\Temp\EPRTR\Acces\Public_Database_2015-12-09.mdb,DestDataset_CSV,S:\Temp\EPRTR\Acces\CSV
    BLOCKING = Yes
    SUCCEEDED -> WorkspaceRunner_2
WorkspaceRunner_2
    WORKSPACE_FILE = $(FME_MF_DIR)zipcsv.fmw
    WORKSPACE_PARAMETERS = SourceDataset_PATH,S:\Temp\EPRTR\Acces\CSV,DestZIP,S:\Temp\EPRTR\Acces\CSV\Public_DB.zip
    BLOCKING = No
