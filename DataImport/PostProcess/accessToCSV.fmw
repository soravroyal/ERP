FME workspace accessToCSV.fmw

Parameters:
- SourceDataset_MDB_ADO = S:\Temp\EPRTR\Acces\Public_Database_2015-12-09.mdb   # Source Microsoft Access Database File(s)
- DestDataset_CSV = S:\Temp\EPRTR\Acces\CSV   # Destination CSV (CommaSeparatedValue) Folder

Readers:
- MDB_ADO_1: MDB_ADO from $(SourceDataset_MDB_ADO)

Writers:
- CSV_1: CSV to $(DestDataset_CSV)

POLLUTANTTRANSFER (reader MDB_ADO_1)
    attributes: PollutantTransferID long, FacilityReportID long, PollutantCode text(255), PollutantName text(255), PollutantGroupCode text(255), PollutantGroupName text(255), PollutantCAS text(20), MethodBasisCode text(255), MethodBasisName text(255), Quantity double, QuantityUnitCode text(255), QuantityUnitName text(255), ConfidentialIndicator yesno, ConfidentialityReasonCode text(255), ConfidentialityReasonName text(255), RemarkText memo
    -> PT_TRIM
PT_TRIM: AttributeTrimmer
    TRIM_TYPE = Both
    SRC_ATTRS = FacilityReportID,ConfidentialIndicator,ConfidentialityReasonCode,ConfidentialityReasonName,MethodBasisCode,MethodBasisName,PollutantCAS,PollutantCode,PollutantGroupCode,PollutantGroupName,PollutantName,PollutantTransferID,Quantity,QuantityUnitCode,QuantityUnitName,RemarkText
    TRIM_TO_NONE = Yes
    -> PT_TAB
PT_TAB: StringReplacer
    FIND_TEXT = \t
    NO_MATCH = _FME_NO_OP_
    REPLACE_TEXT = " "
    REGEXP = no
    CASE = no
    SRC_ATTRS = ConfidentialIndicator,ConfidentialityReasonCode,ConfidentialityReasonName,FacilityReportID,MethodBasisCode,MethodBasisName,PollutantCAS,PollutantCode,PollutantGroupCode,PollutantGroupName,PollutantName,PollutantTransferID,Quantity,QuantityUnitCode,QuantityUnitName,RemarkText
    -> PT_CR
PT_CR: StringReplacer
    FIND_TEXT = \r\n
    NO_MATCH = _FME_NO_OP_
    REPLACE_TEXT = " "
    REGEXP = no
    CASE = no
    SRC_ATTRS = ConfidentialIndicator,ConfidentialityReasonCode,ConfidentialityReasonName,FacilityReportID,MethodBasisCode,MethodBasisName,PollutantCAS,PollutantCode,PollutantGroupCode,PollutantGroupName,PollutantName,PollutantTransferID,Quantity,QuantityUnitCode,QuantityUnitName,RemarkText
    -> PT_NEWLINE
PT_NEWLINE: StringReplacer
    FIND_TEXT = \n
    NO_MATCH = _FME_NO_OP_
    REGEXP = no
    CASE = no
    SRC_ATTRS = ConfidentialIndicator,ConfidentialityReasonCode,ConfidentialityReasonName,FacilityReportID,MethodBasisCode,MethodBasisName,PollutantCAS,PollutantCode,PollutantGroupCode,PollutantGroupName,PollutantName,PollutantTransferID,Quantity,QuantityUnitCode,QuantityUnitName,RemarkText
    -> StringReplacer_5
StringReplacer_5
    FIND_TEXT = "\t"
    NO_MATCH = _FME_NO_OP_
    REPLACE_TEXT = " "
    REGEXP = no
    CASE = no
    SRC_ATTRS = ConfidentialityReasonCode,ConfidentialIndicator,ConfidentialityReasonName,FacilityReportID,MethodBasisCode,MethodBasisName,PollutantCAS,PollutantCode,PollutantGroupCode,PollutantGroupName,PollutantName,PollutantTransferID,Quantity,QuantityUnitCode,QuantityUnitName,RemarkText
    -> POLLUTANTTRANSFER (writer CSV_1)
POLLUTANTTRANSFER (writer CSV_1)
    attributes: PollutantTransferID int, FacilityReportID int, PollutantCode text, PollutantName text, PollutantGroupCode text, PollutantGroupName text, PollutantCAS text, MethodBasisCode text, MethodBasisName text, Quantity float, QuantityUnitCode text, QuantityUnitName text, ConfidentialIndicator logical, ConfidentialityReasonCode text, ConfidentialityReasonName text, RemarkText text
POLLUTANTRELEASEANDTRANSFERREPORT (reader MDB_ADO_1)
    attributes: PollutantReleaseAndTransferReportID long, CountryCode text(255), CountryName text(255), ReportingYear long, CoordinateSystemCode text(255), CoordinateSystemName text(255), RemarkText memo, CdrUrl text(255), CdrUploaded datetime, CdrReleased datetime, ForReview datetime, Published datetime, ResubmitReason memo
    -> PRTR_TRIM
PRTR_TRIM: AttributeTrimmer
    TRIM_TYPE = Both
    SRC_ATTRS = RemarkText,CdrReleased,CdrUploaded,CdrUrl,CoordinateSystemCode,CoordinateSystemName,CountryCode,CountryName,ForReview,PollutantReleaseAndTransferReportID,Published,ReportingYear,ResubmitReason
    TRIM_TO_NONE = Yes
    -> PRTR_TAB
PRTR_TAB: StringReplacer
    FIND_TEXT = \t
    NO_MATCH = _FME_NO_OP_
    REPLACE_TEXT = " "
    REGEXP = no
    CASE = no
    SRC_ATTRS = RemarkText,CdrReleased,CdrUploaded,CdrUrl,CoordinateSystemCode,CoordinateSystemName,CountryCode,CountryName,ForReview,PollutantReleaseAndTransferReportID,Published,ReportingYear,ResubmitReason
    -> PRTR_CR
PRTR_CR: StringReplacer
    FIND_TEXT = \r\n
    NO_MATCH = _FME_NO_OP_
    REPLACE_TEXT = " "
    REGEXP = no
    CASE = no
    SRC_ATTRS = CoordinateSystemCode,CdrReleased,CdrUploaded,CdrUrl,CoordinateSystemName,CountryCode,CountryName,ForReview,PollutantReleaseAndTransferReportID,Published,RemarkText,ReportingYear,ResubmitReason
    -> PRTR_NEWLINE
PRTR_NEWLINE: StringReplacer
    FIND_TEXT = \n
    NO_MATCH = _FME_NO_OP_
    REGEXP = no
    CASE = no
    SRC_ATTRS = CoordinateSystemCode,CdrReleased,CdrUploaded,CdrUrl,CoordinateSystemName,CountryCode,CountryName,ForReview,PollutantReleaseAndTransferReportID,Published,RemarkText,ReportingYear,ResubmitReason
    -> StringReplacer_6
StringReplacer_6
    FIND_TEXT = "\t"
    NO_MATCH = _FME_NO_OP_
    REPLACE_TEXT = " "
    REGEXP = no
    CASE = no
    SRC_ATTRS = CdrUrl,CdrReleased,CdrUploaded,CoordinateSystemCode,CoordinateSystemName,CountryCode,CountryName,ForReview,PollutantReleaseAndTransferReportID,Published,RemarkText,ReportingYear,ResubmitReason
    -> POLLUTANTRELEASEANDTRANSFERREPORT (writer CSV_1)
POLLUTANTRELEASEANDTRANSFERREPORT (writer CSV_1)
    attributes: PollutantReleaseAndTransferReportID int, CountryCode text, CountryName text, ReportingYear int, CoordinateSystemCode text, CoordinateSystemName text, RemarkText text, CdrUrl text, CdrUploaded char(20), CdrReleased char(20), ForReview char(20), Published char(20), ResubmitReason text
POLLUTANTRELEASEMETHODUSED (reader MDB_ADO_1)
    attributes: PollutantReleaseMethodUsedID long, PollutantReleaseID long, MethodTypeCode text(255), MethodTypeName text(255), MethodDesignation text(255)
    -> PRM_TRIM
PRM_TRIM: AttributeTrimmer
    TRIM_TYPE = Both
    SRC_ATTRS = MethodDesignation,MethodTypeCode,MethodTypeName,PollutantReleaseID,PollutantReleaseMethodUsedID
    TRIM_TO_NONE = Yes
    -> PRM_TAB
PRM_TAB: StringReplacer
    FIND_TEXT = \t
    NO_MATCH = _FME_NO_OP_
    REPLACE_TEXT = " "
    REGEXP = no
    CASE = no
    SRC_ATTRS = PollutantReleaseID,MethodDesignation,MethodTypeCode,MethodTypeName,PollutantReleaseMethodUsedID
    -> PRM_CR
PRM_CR: StringReplacer
    FIND_TEXT = \r\n
    NO_MATCH = _FME_NO_OP_
    REPLACE_TEXT = " "
    REGEXP = no
    CASE = no
    SRC_ATTRS = MethodDesignation,MethodTypeCode,MethodTypeName,PollutantReleaseID,PollutantReleaseMethodUsedID
    -> PRM_NEWLINE
PRM_NEWLINE: StringReplacer
    FIND_TEXT = \n
    NO_MATCH = _FME_NO_OP_
    REGEXP = no
    CASE = no
    SRC_ATTRS = MethodDesignation,MethodTypeCode,MethodTypeName,PollutantReleaseID,PollutantReleaseMethodUsedID
    -> StringReplacer
StringReplacer
    FIND_TEXT = "\t"
    NO_MATCH = _FME_NO_OP_
    REPLACE_TEXT = " "
    REGEXP = no
    CASE = no
    SRC_ATTRS = MethodDesignation,MethodTypeCode,MethodTypeName,PollutantReleaseID,PollutantReleaseMethodUsedID
    -> POLLUTANTRELEASEMETHODUSED (writer CSV_1)
POLLUTANTRELEASEMETHODUSED (writer CSV_1)
    attributes: PollutantReleaseMethodUsedID int, PollutantReleaseID int, MethodTypeCode text, MethodTypeName text, MethodDesignation text
FACILITYREPORT (reader MDB_ADO_1)
    attributes: FacilityReportID long, PollutantReleaseAndTransferReportID long, FacilityID long, NationalID text(255), ParentCompanyName text(255), FacilityName text(255), StreetName text(255), BuildingNumber text(255), City text(255), PostalCode text(50), CountryCode text(255), CountryName text(255), Lat double, Long double, RBDGeoCode text(255), RBDGeoName text(255), NUTSRegionGeoCode text(255), NUTSRegionGeoName text(255), RBDSourceCode text(255), RBDSourceName text(255), NUTSRegionSourceCode text(255), NUTSRegionSourceName text(255), NACEMainEconomicActivityCode text(255), NACEMainEconomicActivityName text(255), MainEconomicActivityNameSource text(255), CompetentAuthorityName text(255), CompetentAuthorityAddressStreetName text(255), CompetentAuthorityAddressBuildingNumber text(255), CompetentAuthorityAddressCity text(255), CompetentAuthorityAddressPostalCode text(50),
      CompetentAuthorityAddressCountryCode text(255), CompetentAuthorityAddressCountryName text(255), CompetentAuthorityTelephoneCommunication text(50), CompetentAuthorityFaxCommunication text(50), CompetentAuthorityEmailCommunication text(255), CompetentAuthorityContactPersonName text(255), ProductionVolumeProductName text(255), ProductionVolumeQuantity double, ProductionVolumeUnitCode text(255), ProductionVolumeUnitName text(255), TotalIPPCInstallationQuantity long, OperatingHours long, TotalEmployeeQuantity long, WebsiteCommunication text(255), PublicInformation text(255), ConfidentialIndicator yesno, ConfidentialityReasonCode text(255), ConfidentialityReasonName text(255), ProtectVoluntaryData yesno, RemarkText memo, MainIASectorCode text(255), MainIASectorName text(255), MainIAActivityCode text(255), MainIAActivityName text(255), MainIASubActivityCode text(255), MainIASubActivityName text(255)
    -> FR_TRIM
FR_TRIM: AttributeTrimmer
    TRIM_TYPE = Both
    SRC_ATTRS = CountryCode,CountryName,PollutantReleaseAndTransferReportID,RemarkText,BuildingNumber,City,CompetentAuthorityAddressBuildingNumber,CompetentAuthorityAddressCity,CompetentAuthorityAddressCountryCode,CompetentAuthorityAddressCountryName,CompetentAuthorityAddressPostalCode,CompetentAuthorityAddressStreetName,CompetentAuthorityContactPersonName,CompetentAuthorityEmailCommunication,CompetentAuthorityFaxCommunication,CompetentAuthorityName,CompetentAuthorityTelephoneCommunication,ConfidentialIndicator,ConfidentialityReasonCode,ConfidentialityReasonName,FacilityID,FacilityName,FacilityReportID,Lat,Long,MainEconomicActivityNameSource,MainIAActivityCode,MainIAActivityName,MainIASectorCode,MainIASectorName,MainIASubActivityCode,MainIASubActivityName,NACEMainEconomicActivityCode,NACEMainEconomicActivityName,NationalID,NUTSRegionGeoCode,NUTSRegionGeoName,NUTSRegionSourceCode,NUTSRegionSourceName,OperatingHours,ParentCompanyName,PostalCode,ProductionVolumeProductName,ProductionVolumeQuantity,ProductionVolumeUnitCode,ProductionVolumeUnitName,ProtectVoluntaryData,PublicInformation,RBDGeoCode,RBDGeoName,RBDSourceCode,RBDSourceName,StreetName,TotalEmployeeQuantity,TotalIPPCInstallationQuantity,WebsiteCommunication
    TRIM_TO_NONE = Yes
    -> FR_TAB
FR_TAB: StringReplacer
    FIND_TEXT = \t
    NO_MATCH = _FME_NO_OP_
    REPLACE_TEXT = " "
    REGEXP = no
    CASE = no
    SRC_ATTRS = NUTSRegionSourceCode,BuildingNumber,City,CompetentAuthorityAddressBuildingNumber,CompetentAuthorityAddressCity,CompetentAuthorityAddressCountryCode,CompetentAuthorityAddressCountryName,CompetentAuthorityAddressPostalCode,CompetentAuthorityAddressStreetName,CompetentAuthorityContactPersonName,CompetentAuthorityEmailCommunication,CompetentAuthorityFaxCommunication,CompetentAuthorityName,CompetentAuthorityTelephoneCommunication,ConfidentialIndicator,ConfidentialityReasonCode,ConfidentialityReasonName,CountryCode,CountryName,FacilityID,FacilityName,FacilityReportID,Lat,Long,MainEconomicActivityNameSource,MainIAActivityCode,MainIAActivityName,MainIASectorCode,MainIASectorName,MainIASubActivityCode,MainIASubActivityName,NACEMainEconomicActivityCode,NACEMainEconomicActivityName,NationalID,NUTSRegionGeoCode,NUTSRegionGeoName,NUTSRegionSourceName,OperatingHours,ParentCompanyName,PollutantReleaseAndTransferReportID,PostalCode,ProductionVolumeProductName,ProductionVolumeQuantity,ProductionVolumeUnitCode,ProductionVolumeUnitName,ProtectVoluntaryData,PublicInformation,RBDGeoCode,RBDGeoName,RBDSourceCode,RBDSourceName,RemarkText,StreetName,TotalEmployeeQuantity,TotalIPPCInstallationQuantity,WebsiteCommunication
    -> FR_CR
FR_CR: StringReplacer
    FIND_TEXT = \r\n
    NO_MATCH = _FME_NO_OP_
    REPLACE_TEXT = " "
    REGEXP = no
    CASE = no
    SRC_ATTRS = CompetentAuthorityAddressBuildingNumber,BuildingNumber,City,CompetentAuthorityAddressCity,CompetentAuthorityAddressCountryCode,CompetentAuthorityAddressCountryName,CompetentAuthorityAddressPostalCode,CompetentAuthorityAddressStreetName,CompetentAuthorityContactPersonName,CompetentAuthorityEmailCommunication,CompetentAuthorityFaxCommunication,CompetentAuthorityName,CompetentAuthorityTelephoneCommunication,ConfidentialIndicator,ConfidentialityReasonCode,ConfidentialityReasonName,CountryCode,CountryName,FacilityID,FacilityName,FacilityReportID,Lat,Long,MainEconomicActivityNameSource,MainIAActivityCode,MainIAActivityName,MainIASectorCode,MainIASectorName,MainIASubActivityCode,MainIASubActivityName,NACEMainEconomicActivityCode,NACEMainEconomicActivityName,NationalID,NUTSRegionGeoCode,NUTSRegionGeoName,NUTSRegionSourceCode,NUTSRegionSourceName,OperatingHours,ParentCompanyName,PollutantReleaseAndTransferReportID,PostalCode,ProductionVolumeProductName,ProductionVolumeQuantity,ProductionVolumeUnitCode,ProductionVolumeUnitName,ProtectVoluntaryData,PublicInformation,RBDGeoCode,RBDGeoName,RBDSourceCode,RBDSourceName,RemarkText,StreetName,TotalEmployeeQuantity,TotalIPPCInstallationQuantity,WebsiteCommunication
    -> FR_NEWLINE
FR_NEWLINE: StringReplacer
    FIND_TEXT = \n
    NO_MATCH = _FME_NO_OP_
    REGEXP = no
    CASE = no
    SRC_ATTRS = CompetentAuthorityAddressCountryCode,BuildingNumber,City,CompetentAuthorityAddressBuildingNumber,CompetentAuthorityAddressCity,CompetentAuthorityAddressCountryName,CompetentAuthorityAddressPostalCode,CompetentAuthorityAddressStreetName,CompetentAuthorityContactPersonName,CompetentAuthorityEmailCommunication,CompetentAuthorityFaxCommunication,CompetentAuthorityName,CompetentAuthorityTelephoneCommunication,ConfidentialIndicator,ConfidentialityReasonCode,ConfidentialityReasonName,CountryCode,CountryName,FacilityID,FacilityName,FacilityReportID,Lat,Long,MainEconomicActivityNameSource,MainIAActivityCode,MainIAActivityName,MainIASectorCode,MainIASectorName,MainIASubActivityCode,MainIASubActivityName,NACEMainEconomicActivityCode,NACEMainEconomicActivityName,NationalID,NUTSRegionGeoCode,NUTSRegionGeoName,NUTSRegionSourceCode,NUTSRegionSourceName,OperatingHours,ParentCompanyName,PollutantReleaseAndTransferReportID,PostalCode,ProductionVolumeProductName,ProductionVolumeQuantity,ProductionVolumeUnitCode,ProductionVolumeUnitName,ProtectVoluntaryData,PublicInformation,RBDGeoCode,RBDGeoName,RBDSourceCode,RBDSourceName,RemarkText,StreetName,TotalEmployeeQuantity,TotalIPPCInstallationQuantity,WebsiteCommunication
    -> StringReplacer_4
StringReplacer_4
    FIND_TEXT = "\t"
    NO_MATCH = _FME_NO_OP_
    REPLACE_TEXT = " "
    REGEXP = no
    CASE = no
    SRC_ATTRS = ConfidentialIndicator,ConfidentialityReasonCode,ConfidentialityReasonName,FacilityReportID,RemarkText,BuildingNumber,City,CompetentAuthorityAddressBuildingNumber,CompetentAuthorityAddressCity,CompetentAuthorityAddressCountryCode,CompetentAuthorityAddressCountryName,CompetentAuthorityAddressPostalCode,CompetentAuthorityAddressStreetName,CompetentAuthorityContactPersonName,CompetentAuthorityEmailCommunication,CompetentAuthorityFaxCommunication,CompetentAuthorityName,CompetentAuthorityTelephoneCommunication,CountryCode,CountryName,FacilityID,FacilityName,Lat,Long,MainEconomicActivityNameSource,MainIAActivityCode,MainIAActivityName,MainIASectorCode,MainIASectorName,MainIASubActivityCode,MainIASubActivityName,NACEMainEconomicActivityCode,NACEMainEconomicActivityName,NationalID,NUTSRegionGeoCode,NUTSRegionGeoName,NUTSRegionSourceCode,NUTSRegionSourceName,OperatingHours,ParentCompanyName,PollutantReleaseAndTransferReportID,PostalCode,ProductionVolumeProductName,ProductionVolumeQuantity,ProductionVolumeUnitCode,ProductionVolumeUnitName,ProtectVoluntaryData,PublicInformation,RBDGeoCode,RBDGeoName,RBDSourceCode,RBDSourceName,StreetName,TotalEmployeeQuantity,TotalIPPCInstallationQuantity,WebsiteCommunication
    -> FACILITYREPORT (writer CSV_1)
FACILITYREPORT (writer CSV_1)
    attributes: FacilityReportID int, PollutantReleaseAndTransferReportID int, FacilityID int, NationalID text, ParentCompanyName text, FacilityName text, StreetName text, BuildingNumber text, City text, PostalCode text, CountryCode text, CountryName text, Lat float, Long float, RBDGeoCode text, RBDGeoName text, NUTSRegionGeoCode text, NUTSRegionGeoName text, RBDSourceCode text, RBDSourceName text, NUTSRegionSourceCode text, NUTSRegionSourceName text, NACEMainEconomicActivityCode text, NACEMainEconomicActivityName text, MainEconomicActivityNameSource text, CompetentAuthorityName text, CompetentAuthorityAddressStreetName text, CompetentAuthorityAddressBuildingNumber text, CompetentAuthorityAddressCity text, CompetentAuthorityAddressPostalCode text,
      CompetentAuthorityAddressCountryCode text, CompetentAuthorityAddressCountryName text, CompetentAuthorityTelephoneCommunication text, CompetentAuthorityFaxCommunication text, CompetentAuthorityEmailCommunication text, CompetentAuthorityContactPersonName text, ProductionVolumeProductName text, ProductionVolumeQuantity float, ProductionVolumeUnitCode text, ProductionVolumeUnitName text, TotalIPPCInstallationQuantity int, OperatingHours int, TotalEmployeeQuantity int, WebsiteCommunication text, PublicInformation text, ConfidentialIndicator logical, ConfidentialityReasonCode text, ConfidentialityReasonName text, ProtectVoluntaryData logical, RemarkText text, MainIASectorCode text, MainIASectorName text, MainIAActivityCode text, MainIAActivityName text, MainIASubActivityCode text, MainIASubActivityName text
EPER2EPRTR_ANNEXIACTIVITY (reader MDB_ADO_1)
    attributes: EPER_Code text(8), EPER_Name text(255), StartYear long, EndYear long, EPRTR_Code text(255), EPRTR_Name text(255), EPRTR_StartYear long
    -> E2E_TRIM
E2E_TRIM: AttributeTrimmer
    TRIM_TYPE = Both
    SRC_ATTRS = EndYear,EPER_Code,EPER_Name,EPRTR_Code,EPRTR_Name,EPRTR_StartYear,StartYear
    TRIM_TO_NONE = Yes
    -> E2E_TAB
E2E_TAB: StringReplacer
    FIND_TEXT = \t
    NO_MATCH = _FME_NO_OP_
    REPLACE_TEXT = " "
    REGEXP = no
    CASE = no
    SRC_ATTRS = EPER_Code,EndYear,EPER_Name,EPRTR_Code,EPRTR_Name,EPRTR_StartYear,StartYear
    -> E2E_CR
E2E_CR: StringReplacer
    FIND_TEXT = \r\n
    NO_MATCH = _FME_NO_OP_
    REPLACE_TEXT = " "
    REGEXP = no
    CASE = no
    SRC_ATTRS = EPER_Name,EndYear,EPER_Code,EPRTR_Code,EPRTR_Name,EPRTR_StartYear,StartYear
    -> E2E_NEWLINE
E2E_NEWLINE: StringReplacer
    FIND_TEXT = \n
    NO_MATCH = _FME_NO_OP_
    REGEXP = no
    CASE = no
    SRC_ATTRS = EPRTR_Name,EndYear,EPER_Code,EPER_Name,EPRTR_Code,EPRTR_StartYear,StartYear
    -> StringReplacer_7
StringReplacer_7
    FIND_TEXT = "\t"
    NO_MATCH = _FME_NO_OP_
    REPLACE_TEXT = " "
    REGEXP = no
    CASE = no
    SRC_ATTRS = EPER_Name,EndYear,EPER_Code,EPRTR_Code,EPRTR_Name,EPRTR_StartYear,StartYear
    -> EPER2EPRTR_ANNEXIACTIVITY (writer CSV_1)
EPER2EPRTR_ANNEXIACTIVITY (writer CSV_1)
    attributes: EPER_Code text, EPER_Name text, StartYear int, EndYear int, EPRTR_Code text, EPRTR_Name text, EPRTR_StartYear int
EPER2EPRTR_NACEACTIVITY (reader MDB_ADO_1)
    attributes: EPER_Name text(255), EPER_Code text(8), EPER_Section text(255), EPER_SubSection text(255), LOV_NACEActivityID autonumber, EPRTR_Name text(255), EPRTR_Code text(255), EPRTR_StartYear long, EPRTR_EndYear long, EPRTR_ParentID long
    -> E2EN_TRIM
E2EN_TRIM: AttributeTrimmer
    TRIM_TYPE = Both
    SRC_ATTRS = EPER_Code,EPER_Name,EPRTR_Code,EPRTR_Name,EPRTR_StartYear,EPER_Section,EPER_SubSection,EPRTR_EndYear,EPRTR_ParentID,LOV_NACEActivityID
    TRIM_TO_NONE = Yes
    -> E2EN_TAB
E2EN_TAB: StringReplacer
    FIND_TEXT = \t
    NO_MATCH = _FME_NO_OP_
    REPLACE_TEXT = " "
    REGEXP = no
    CASE = no
    SRC_ATTRS = EPER_Code,EPER_Name,EPER_SubSection,EPRTR_Code,EPRTR_Name,EPRTR_StartYear,EPER_Section,EPRTR_EndYear,EPRTR_ParentID,LOV_NACEActivityID
    -> E2EN_CR
E2EN_CR: StringReplacer
    FIND_TEXT = \r\n
    NO_MATCH = _FME_NO_OP_
    REPLACE_TEXT = " "
    REGEXP = no
    CASE = no
    SRC_ATTRS = EPER_Code,EPER_Name,EPRTR_Code,EPRTR_EndYear,EPRTR_Name,EPRTR_StartYear,EPER_Section,EPER_SubSection,EPRTR_ParentID,LOV_NACEActivityID
    -> E2EN_NEWLINE
E2EN_NEWLINE: StringReplacer
    FIND_TEXT = \n
    NO_MATCH = _FME_NO_OP_
    REGEXP = no
    CASE = no
    SRC_ATTRS = EPER_Code,EPER_Name,EPER_SubSection,EPRTR_Code,EPRTR_Name,EPRTR_StartYear,EPER_Section,EPRTR_EndYear,EPRTR_ParentID,LOV_NACEActivityID
    -> StringReplacer_8
StringReplacer_8
    FIND_TEXT = "\t"
    NO_MATCH = _FME_NO_OP_
    REPLACE_TEXT = " "
    REGEXP = no
    CASE = no
    SRC_ATTRS = EPRTR_Code,EPER_Code,EPER_Name,EPER_Section,EPER_SubSection,EPRTR_EndYear,EPRTR_Name,EPRTR_ParentID,EPRTR_StartYear,LOV_NACEActivityID
    -> EPER2EPRTR_NACEACTIVITY (writer CSV_1)
EPER2EPRTR_NACEACTIVITY (writer CSV_1)
    attributes: EPER_Name text, EPER_Code text, EPER_Section text, EPER_SubSection text, LOV_NACEActivityID int, EPRTR_Name text, EPRTR_Code text, EPRTR_StartYear int, EPRTR_EndYear int, EPRTR_ParentID int
WASTETRANSFER (reader MDB_ADO_1)
    attributes: WasteTransferID long, FacilityReportID long, WasteTypeCode text(255), WasteTypeName text(255), WasteTreatmentCode text(255), WasteTreatmentName text(255), MethodBasisCode text(255), MethodBasisName text(255), Quantity double, QuantityUnitCode text(255), QuantityUnitName text(255), WasteHandlerPartyName text(255), WasteHandlerPartyAddressStreetName text(255), WasteHandlerPartyAddressBuildingNumber text(255), WasteHandlerPartyAddressCity text(255), WasteHandlerPartyAddressPostalCode text(50), WasteHandlerPartyAddressCountryCode text(255), WasteHandlerPartyAddressCountryName text(255), WasteHandlerPartySiteAddressStreetName text(255), WasteHandlerPartySiteAddressBuildingNumber text(255), WasteHandlerPartySiteAddressCity text(255), WasteHandlerPartySiteAddressPostalCode text(50), WasteHandlerPartySiteAddressCountryCode text(255), WasteHandlerPartySiteAddressCountryName text(255), ConfidentialIndicator yesno, ConfidentialityReasonCode text(255), ConfidentialityReasonName text(255), RemarkText memo
    -> WT_TRIM
WT_TRIM: AttributeTrimmer
    TRIM_TYPE = Right
    SRC_ATTRS = ConfidentialityReasonCode,ConfidentialIndicator,ConfidentialityReasonName,FacilityReportID,MethodBasisCode,MethodBasisName,Quantity,QuantityUnitCode,QuantityUnitName,RemarkText,WasteHandlerPartyAddressBuildingNumber,WasteHandlerPartyAddressCity,WasteHandlerPartyAddressCountryCode,WasteHandlerPartyAddressCountryName,WasteHandlerPartyAddressPostalCode,WasteHandlerPartyAddressStreetName,WasteHandlerPartyName,WasteHandlerPartySiteAddressBuildingNumber,WasteHandlerPartySiteAddressCity,WasteHandlerPartySiteAddressCountryCode,WasteHandlerPartySiteAddressCountryName,WasteHandlerPartySiteAddressPostalCode,WasteHandlerPartySiteAddressStreetName,WasteTransferID,WasteTreatmentCode,WasteTreatmentName,WasteTypeCode,WasteTypeName
    TRIM_TO_NONE = Yes
    -> WT_TAB
WT_TAB: StringReplacer
    FIND_TEXT = \t
    NO_MATCH = _FME_NO_OP_
    REPLACE_TEXT = " "
    REGEXP = no
    CASE = no
    SRC_ATTRS = ConfidentialityReasonName,ConfidentialIndicator,ConfidentialityReasonCode,FacilityReportID,MethodBasisCode,MethodBasisName,Quantity,QuantityUnitCode,QuantityUnitName,RemarkText,WasteHandlerPartyAddressBuildingNumber,WasteHandlerPartyAddressCity,WasteHandlerPartyAddressCountryCode,WasteHandlerPartyAddressCountryName,WasteHandlerPartyAddressPostalCode,WasteHandlerPartyAddressStreetName,WasteHandlerPartyName,WasteHandlerPartySiteAddressBuildingNumber,WasteHandlerPartySiteAddressCity,WasteHandlerPartySiteAddressCountryCode,WasteHandlerPartySiteAddressCountryName,WasteHandlerPartySiteAddressPostalCode,WasteHandlerPartySiteAddressStreetName,WasteTransferID,WasteTreatmentCode,WasteTreatmentName,WasteTypeCode,WasteTypeName
    -> WT_CR
WT_CR: StringReplacer
    FIND_TEXT = \r\n
    NO_MATCH = _FME_NO_OP_
    REPLACE_TEXT = " "
    REGEXP = no
    CASE = no
    SRC_ATTRS = FacilityReportID,ConfidentialIndicator,ConfidentialityReasonCode,ConfidentialityReasonName,MethodBasisCode,MethodBasisName,Quantity,QuantityUnitCode,QuantityUnitName,RemarkText,WasteHandlerPartyAddressBuildingNumber,WasteHandlerPartyAddressCity,WasteHandlerPartyAddressCountryCode,WasteHandlerPartyAddressCountryName,WasteHandlerPartyAddressPostalCode,WasteHandlerPartyAddressStreetName,WasteHandlerPartyName,WasteHandlerPartySiteAddressBuildingNumber,WasteHandlerPartySiteAddressCity,WasteHandlerPartySiteAddressCountryCode,WasteHandlerPartySiteAddressCountryName,WasteHandlerPartySiteAddressPostalCode,WasteHandlerPartySiteAddressStreetName,WasteTransferID,WasteTreatmentCode,WasteTreatmentName,WasteTypeCode,WasteTypeName
    -> WT_NEWLINE
WT_NEWLINE: StringReplacer
    FIND_TEXT = \n
    NO_MATCH = _FME_NO_OP_
    REGEXP = no
    CASE = no
    SRC_ATTRS = ConfidentialityReasonName,ConfidentialIndicator,ConfidentialityReasonCode,FacilityReportID,MethodBasisCode,MethodBasisName,Quantity,QuantityUnitCode,QuantityUnitName,RemarkText,WasteHandlerPartyAddressBuildingNumber,WasteHandlerPartyAddressCity,WasteHandlerPartyAddressCountryCode,WasteHandlerPartyAddressCountryName,WasteHandlerPartyAddressPostalCode,WasteHandlerPartyAddressStreetName,WasteHandlerPartyName,WasteHandlerPartySiteAddressBuildingNumber,WasteHandlerPartySiteAddressCity,WasteHandlerPartySiteAddressCountryCode,WasteHandlerPartySiteAddressCountryName,WasteHandlerPartySiteAddressPostalCode,WasteHandlerPartySiteAddressStreetName,WasteTransferID,WasteTreatmentCode,WasteTreatmentName,WasteTypeCode,WasteTypeName
    -> StringReplacer_3
StringReplacer_3
    FIND_TEXT = "\t"
    NO_MATCH = _FME_NO_OP_
    REPLACE_TEXT = " "
    REGEXP = no
    CASE = no
    SRC_ATTRS = FacilityReportID,ConfidentialIndicator,ConfidentialityReasonCode,ConfidentialityReasonName,MethodBasisCode,MethodBasisName,Quantity,QuantityUnitCode,QuantityUnitName,RemarkText,WasteHandlerPartyAddressBuildingNumber,WasteHandlerPartyAddressCity,WasteHandlerPartyAddressCountryCode,WasteHandlerPartyAddressCountryName,WasteHandlerPartyAddressPostalCode,WasteHandlerPartyAddressStreetName,WasteHandlerPartyName,WasteHandlerPartySiteAddressBuildingNumber,WasteHandlerPartySiteAddressCity,WasteHandlerPartySiteAddressCountryCode,WasteHandlerPartySiteAddressCountryName,WasteHandlerPartySiteAddressPostalCode,WasteHandlerPartySiteAddressStreetName,WasteTransferID,WasteTreatmentCode,WasteTreatmentName,WasteTypeCode,WasteTypeName
    -> WASTETRANSFER (writer CSV_1)
WASTETRANSFER (writer CSV_1)
    attributes: WasteTransferID int, FacilityReportID int, WasteTypeCode text, WasteTypeName text, WasteTreatmentCode text, WasteTreatmentName text, MethodBasisCode text, MethodBasisName text, Quantity float, QuantityUnitCode text, QuantityUnitName text, WasteHandlerPartyName text, WasteHandlerPartyAddressStreetName text, WasteHandlerPartyAddressBuildingNumber text, WasteHandlerPartyAddressCity text, WasteHandlerPartyAddressPostalCode text, WasteHandlerPartyAddressCountryCode text, WasteHandlerPartyAddressCountryName text, WasteHandlerPartySiteAddressStreetName text, WasteHandlerPartySiteAddressBuildingNumber text, WasteHandlerPartySiteAddressCity text, WasteHandlerPartySiteAddressPostalCode text, WasteHandlerPartySiteAddressCountryCode text, WasteHandlerPartySiteAddressCountryName text, ConfidentialIndicator logical, ConfidentialityReasonCode text, ConfidentialityReasonName text, RemarkText text
ACTIVITY (reader MDB_ADO_1)
    attributes: ActivityID long, FacilityReportID long, FacilityReportName text(255), AnnexIActivityCode text(255), AnnexIActivityName text(255), AnnexIActivityIPPCCode text(255), RankingNumeric long, MainActivityIndicator yesno
    -> A_TRIM
A_TRIM: AttributeTrimmer
    TRIM_TYPE = Both
    SRC_ATTRS = ActivityID,AnnexIActivityCode,AnnexIActivityIPPCCode,AnnexIActivityName,FacilityReportID,FacilityReportName,MainActivityIndicator,RankingNumeric
    TRIM_TO_NONE = Yes
    -> A_TAB
A_TAB: StringReplacer
    FIND_TEXT = \t
    NO_MATCH = _FME_NO_OP_
    REPLACE_TEXT = " "
    REGEXP = no
    CASE = no
    SRC_ATTRS = FacilityReportID,FacilityReportName,ActivityID,AnnexIActivityCode,AnnexIActivityIPPCCode,AnnexIActivityName,MainActivityIndicator,RankingNumeric
    -> A_CR
A_CR: StringReplacer
    FIND_TEXT = \r\n
    NO_MATCH = _FME_NO_OP_
    REPLACE_TEXT = " "
    REGEXP = no
    CASE = no
    SRC_ATTRS = FacilityReportID,ActivityID,AnnexIActivityCode,AnnexIActivityIPPCCode,AnnexIActivityName,FacilityReportName,MainActivityIndicator,RankingNumeric
    -> A_NEWLINE
A_NEWLINE: StringReplacer
    FIND_TEXT = \n
    NO_MATCH = _FME_NO_OP_
    REGEXP = no
    CASE = no
    SRC_ATTRS = FacilityReportID,ActivityID,AnnexIActivityCode,AnnexIActivityIPPCCode,AnnexIActivityName,FacilityReportName,MainActivityIndicator,RankingNumeric
    -> StringReplacer_2
StringReplacer_2
    FIND_TEXT = "\t"
    NO_MATCH = _FME_NO_OP_
    REPLACE_TEXT = " "
    REGEXP = no
    CASE = no
    SRC_ATTRS = AnnexIActivityIPPCCode,ActivityID,AnnexIActivityCode,AnnexIActivityName,FacilityReportID,FacilityReportName,MainActivityIndicator,RankingNumeric
    -> ACTIVITY (writer CSV_1)
ACTIVITY (writer CSV_1)
    attributes: ActivityID int, FacilityReportID int, FacilityReportName text, AnnexIActivityCode text, AnnexIActivityName text, AnnexIActivityIPPCCode text, RankingNumeric int, MainActivityIndicator logical
UPLOADEDREPORTS (reader MDB_ADO_1)
    attributes: Code text(255), LOV_CountryID long, ReportingYear long, CurrentlyShown long, RemarkText memo, CdrUrl text(255), CdrUploaded datetime, CdrReleased datetime, ForReview datetime, Published datetime, ResubmitReason memo, ImportedToEPRTRMaster datetime
    -> UR_TRIM
UR_TRIM: AttributeTrimmer
    TRIM_TYPE = Both
    SRC_ATTRS = CdrUploaded,CdrReleased,CdrUrl,Code,CurrentlyShown,ForReview,ImportedToEPRTRMaster,LOV_CountryID,Published,RemarkText,ReportingYear,ResubmitReason
    TRIM_TO_NONE = Yes
    -> UR_TAB
UR_TAB: StringReplacer
    FIND_TEXT = \t
    NO_MATCH = _FME_NO_OP_
    REPLACE_TEXT = " "
    REGEXP = no
    CASE = no
    SRC_ATTRS = CdrReleased,CdrUploaded,CdrUrl,Code,CurrentlyShown,ForReview,ImportedToEPRTRMaster,LOV_CountryID,Published,RemarkText,ReportingYear,ResubmitReason
    -> UR_CR
UR_CR: StringReplacer
    FIND_TEXT = \r\n
    NO_MATCH = _FME_NO_OP_
    REPLACE_TEXT = " "
    REGEXP = no
    CASE = no
    SRC_ATTRS = CdrUploaded,CdrReleased,CdrUrl,Code,CurrentlyShown,ForReview,ImportedToEPRTRMaster,LOV_CountryID,Published,RemarkText,ReportingYear,ResubmitReason
    -> UR_NEWLINE
UR_NEWLINE: StringReplacer
    FIND_TEXT = \n
    NO_MATCH = _FME_NO_OP_
    REGEXP = no
    CASE = no
    SRC_ATTRS = CdrUploaded,CdrReleased,CdrUrl,Code,CurrentlyShown,ForReview,ImportedToEPRTRMaster,LOV_CountryID,Published,RemarkText,ReportingYear,ResubmitReason
    -> StringReplacer_9
StringReplacer_9
    FIND_TEXT = "\t"
    NO_MATCH = _FME_NO_OP_
    REPLACE_TEXT = " "
    REGEXP = no
    CASE = no
    SRC_ATTRS = Code,CdrReleased,CdrUploaded,CdrUrl,CurrentlyShown,ForReview,ImportedToEPRTRMaster,LOV_CountryID,Published,RemarkText,ReportingYear,ResubmitReason
    -> UPLOADEDREPORTS (writer CSV_1)
UPLOADEDREPORTS (writer CSV_1)
    attributes: Code text, LOV_CountryID int, ReportingYear int, CurrentlyShown int, RemarkText text, CdrUrl text, CdrUploaded char(20), CdrReleased char(20), ForReview char(20), Published char(20), ResubmitReason text, ImportedToEPRTRMaster char(20)
POLLUTANTRELEASE (reader MDB_ADO_1)
    attributes: PollutantReleaseID long, FacilityReportID long, ReleaseMediumCode text(255), ReleaseMediumName text(255), PollutantCode text(255), PollutantName text(255), PollutantGroupCode text(255), PollutantGroupName text(255), PollutantCAS text(20), MethodBasisCode text(255), MethodBasisName text(255), TotalQuantity double, AccidentalQuantity double, UnitCode text(255), UnitName text(255), ConfidentialIndicator yesno, ConfidentialityReasonCode text(255), ConfidentialityReasonName text(255), RemarkText memo
    -> PR_TRIM_2
PR_TRIM_2: AttributeTrimmer
    TRIM_TYPE = Both
    SRC_ATTRS = RemarkText,AccidentalQuantity,ConfidentialIndicator,ConfidentialityReasonCode,ConfidentialityReasonName,FacilityReportID,MethodBasisCode,MethodBasisName,PollutantCAS,PollutantCode,PollutantGroupCode,PollutantGroupName,PollutantName,PollutantReleaseID,ReleaseMediumCode,ReleaseMediumName,TotalQuantity,UnitCode,UnitName
    TRIM_TO_NONE = Yes
    -> PR_TAB
PR_TAB: StringReplacer
    FIND_TEXT = \t
    NO_MATCH = _FME_NO_OP_
    REPLACE_TEXT = " "
    REGEXP = no
    CASE = no
    SRC_ATTRS = RemarkText,AccidentalQuantity,ConfidentialIndicator,ConfidentialityReasonCode,ConfidentialityReasonName,FacilityReportID,MethodBasisCode,MethodBasisName,PollutantCAS,PollutantCode,PollutantGroupCode,PollutantGroupName,PollutantName,PollutantReleaseID,ReleaseMediumCode,ReleaseMediumName,TotalQuantity,UnitCode,UnitName
    -> PR_CR
PR_CR: StringReplacer
    FIND_TEXT = \r\n
    NO_MATCH = _FME_NO_OP_
    REPLACE_TEXT = " "
    REGEXP = no
    CASE = no
    SRC_ATTRS = RemarkText,AccidentalQuantity,ConfidentialIndicator,ConfidentialityReasonCode,ConfidentialityReasonName,FacilityReportID,MethodBasisCode,MethodBasisName,PollutantCAS,PollutantCode,PollutantGroupCode,PollutantGroupName,PollutantName,PollutantReleaseID,ReleaseMediumCode,ReleaseMediumName,TotalQuantity,UnitCode,UnitName
    -> PR_NEWLINE
PR_NEWLINE: StringReplacer
    FIND_TEXT = \n
    NO_MATCH = _FME_NO_OP_
    REGEXP = no
    CASE = no
    SRC_ATTRS = RemarkText,AccidentalQuantity,ConfidentialIndicator,ConfidentialityReasonCode,ConfidentialityReasonName,FacilityReportID,MethodBasisCode,MethodBasisName,PollutantCAS,PollutantCode,PollutantGroupCode,PollutantGroupName,PollutantName,PollutantReleaseID,ReleaseMediumCode,ReleaseMediumName,TotalQuantity,UnitCode,UnitName
    -> StringReplacer_10
StringReplacer_10
    FIND_TEXT = "\t"
    NO_MATCH = _FME_NO_OP_
    REPLACE_TEXT = " "
    REGEXP = no
    CASE = no
    SRC_ATTRS = ConfidentialityReasonName,PollutantReleaseID,AccidentalQuantity,ConfidentialIndicator,ConfidentialityReasonCode,FacilityReportID,MethodBasisCode,MethodBasisName,PollutantCAS,PollutantCode,PollutantGroupCode,PollutantGroupName,PollutantName,ReleaseMediumCode,ReleaseMediumName,RemarkText,TotalQuantity,UnitCode,UnitName
    -> POLLUTANTRELEASE (writer CSV_1)
POLLUTANTRELEASE (writer CSV_1)
    attributes: PollutantReleaseID int, FacilityReportID int, ReleaseMediumCode text, ReleaseMediumName text, PollutantCode text, PollutantName text, PollutantGroupCode text, PollutantGroupName text, PollutantCAS text, MethodBasisCode text, MethodBasisName text, TotalQuantity float, AccidentalQuantity float, UnitCode text, UnitName text, ConfidentialIndicator logical, ConfidentialityReasonCode text, ConfidentialityReasonName text, RemarkText text
POLLUTANTTRANSFERMETHODUSED (reader MDB_ADO_1)
    attributes: PollutantTransferMethodUsedID long, PollutantTransferID long, MethodTypeCode text(255), MethodTypeName text(255), MethodDesignation text(255)
    -> PTM_TRIM
PTM_TRIM: AttributeTrimmer
    TRIM_TYPE = Both
    SRC_ATTRS = MethodDesignation,MethodTypeCode,MethodTypeName,PollutantTransferID,PollutantTransferMethodUsedID
    TRIM_TO_NONE = Yes
    -> PTM_TAB
PTM_TAB: StringReplacer
    FIND_TEXT = \t
    NO_MATCH = _FME_NO_OP_
    REPLACE_TEXT = " "
    REGEXP = no
    CASE = no
    SRC_ATTRS = MethodDesignation,MethodTypeCode,MethodTypeName,PollutantTransferID,PollutantTransferMethodUsedID
    -> PTM_CR
PTM_CR: StringReplacer
    FIND_TEXT = \r\n
    NO_MATCH = _FME_NO_OP_
    REPLACE_TEXT = " "
    REGEXP = no
    CASE = no
    SRC_ATTRS = MethodDesignation,MethodTypeCode,MethodTypeName,PollutantTransferID,PollutantTransferMethodUsedID
    -> PTM_NEWLINE
PTM_NEWLINE: StringReplacer
    FIND_TEXT = \n
    NO_MATCH = _FME_NO_OP_
    REGEXP = no
    CASE = no
    SRC_ATTRS = MethodDesignation,MethodTypeCode,MethodTypeName,PollutantTransferID,PollutantTransferMethodUsedID
    -> StringReplacer_11
StringReplacer_11
    FIND_TEXT = "\t"
    NO_MATCH = _FME_NO_OP_
    REPLACE_TEXT = " "
    REGEXP = no
    CASE = no
    SRC_ATTRS = MethodDesignation,MethodTypeCode,MethodTypeName,PollutantTransferID,PollutantTransferMethodUsedID
    -> POLLUTANTTRANSFERMETHODUSED (writer CSV_1)
POLLUTANTTRANSFERMETHODUSED (writer CSV_1)
    attributes: PollutantTransferMethodUsedID int, PollutantTransferID int, MethodTypeCode text, MethodTypeName text, MethodDesignation text
FACILITYID_CHANGES (reader MDB_ADO_1)
    attributes: CountryCode text(255), ReportingYear long, FacilityReportID long, NationalID text(255), NewFacilityID long, OldFacilityID long
    -> FC_TRIM
FC_TRIM: AttributeTrimmer
    TRIM_TYPE = Both
    SRC_ATTRS = FacilityReportID,CountryCode,NationalID,NewFacilityID,OldFacilityID,ReportingYear
    TRIM_TO_NONE = Yes
    -> FC_TAB
FC_TAB: StringReplacer
    FIND_TEXT = \t
    NO_MATCH = _FME_NO_OP_
    REPLACE_TEXT = " "
    REGEXP = no
    CASE = no
    SRC_ATTRS = CountryCode,FacilityReportID,NationalID,NewFacilityID,OldFacilityID,ReportingYear
    -> FC_CR
FC_CR: StringReplacer
    FIND_TEXT = \r\n
    NO_MATCH = _FME_NO_OP_
    REPLACE_TEXT = " "
    REGEXP = no
    CASE = no
    SRC_ATTRS = NewFacilityID,CountryCode,FacilityReportID,NationalID,OldFacilityID,ReportingYear
    -> FC_NEWLINE
FC_NEWLINE: StringReplacer
    FIND_TEXT = \n
    NO_MATCH = _FME_NO_OP_
    REGEXP = no
    CASE = no
    SRC_ATTRS = CountryCode,FacilityReportID,NationalID,NewFacilityID,OldFacilityID,ReportingYear
    -> StringReplacer_12
StringReplacer_12
    FIND_TEXT = "\t"
    NO_MATCH = _FME_NO_OP_
    REPLACE_TEXT = " "
    REGEXP = no
    CASE = no
    SRC_ATTRS = NationalID,CountryCode,FacilityReportID,NewFacilityID,OldFacilityID,ReportingYear
    -> FACILITYID_CHANGES (writer CSV_1)
FACILITYID_CHANGES (writer CSV_1)
    attributes: CountryCode text, ReportingYear int, FacilityReportID int, NationalID text, NewFacilityID int, OldFacilityID int
FACILITYID_CHANGES_MINOLDFACILITYID (reader MDB_ADO_1)
    attributes: CountryCode text(255), ReportingYear long, FacilityReportID long, NationalID text(255), NewFacilityID long, OldFacilityID long
    -> FCMOF_TRIM
FCMOF_TRIM: AttributeTrimmer
    TRIM_TYPE = Both
    SRC_ATTRS = CountryCode,FacilityReportID,NationalID,NewFacilityID,OldFacilityID,ReportingYear
    TRIM_TO_NONE = Yes
    -> FCMOF_TAB
FCMOF_TAB: StringReplacer
    FIND_TEXT = \t
    NO_MATCH = _FME_NO_OP_
    REPLACE_TEXT = " "
    REGEXP = no
    CASE = no
    SRC_ATTRS = CountryCode,FacilityReportID,NationalID,NewFacilityID,OldFacilityID,ReportingYear
    -> FCMOF_CR
FCMOF_CR: StringReplacer
    FIND_TEXT = \r\n
    NO_MATCH = _FME_NO_OP_
    REPLACE_TEXT = " "
    REGEXP = no
    CASE = no
    SRC_ATTRS = NewFacilityID,CountryCode,FacilityReportID,NationalID,OldFacilityID,ReportingYear
    -> FCMOF_NEWLINE
FCMOF_NEWLINE: StringReplacer
    FIND_TEXT = \n
    NO_MATCH = _FME_NO_OP_
    REGEXP = no
    CASE = no
    SRC_ATTRS = CountryCode,FacilityReportID,NationalID,NewFacilityID,OldFacilityID,ReportingYear
    -> StringReplacer_13
StringReplacer_13
    FIND_TEXT = "\t"
    NO_MATCH = _FME_NO_OP_
    REPLACE_TEXT = " "
    REGEXP = no
    CASE = no
    SRC_ATTRS = NationalID,CountryCode,FacilityReportID,NewFacilityID,OldFacilityID,ReportingYear
    -> FACILITYID_CHANGES_MINOLDFACILITYID (writer CSV_1)
FACILITYID_CHANGES_MINOLDFACILITYID (writer CSV_1)
    attributes: CountryCode text, ReportingYear int, FacilityReportID int, NationalID text, NewFacilityID int, OldFacilityID int
WASTETRANSFERMETHODUSED (reader MDB_ADO_1)
    attributes: WasteTransferMethodUsedID long, WasteTransferID long, MethodTypeCode text(255), MethodTypeName text(255), MethodDesignation text(255)
    -> FCMOF_TRIM_2
FCMOF_TRIM_2: AttributeTrimmer
    TRIM_TYPE = Both
    SRC_ATTRS = MethodDesignation,MethodTypeCode,MethodTypeName,WasteTransferID,WasteTransferMethodUsedID
    TRIM_TO_NONE = Yes
    -> FCMOF_TAB_2
FCMOF_TAB_2: StringReplacer
    FIND_TEXT = \t
    NO_MATCH = _FME_NO_OP_
    REPLACE_TEXT = " "
    REGEXP = no
    CASE = no
    SRC_ATTRS = MethodTypeCode,MethodDesignation,MethodTypeName,WasteTransferID,WasteTransferMethodUsedID
    -> FCMOF_CR_2
FCMOF_CR_2: StringReplacer
    FIND_TEXT = \r\n
    NO_MATCH = _FME_NO_OP_
    REPLACE_TEXT = " "
    REGEXP = no
    CASE = no
    SRC_ATTRS = MethodDesignation,MethodTypeCode,MethodTypeName,WasteTransferID,WasteTransferMethodUsedID
    -> FCMOF_NEWLINE_2
FCMOF_NEWLINE_2: StringReplacer
    FIND_TEXT = \n
    NO_MATCH = _FME_NO_OP_
    REGEXP = no
    CASE = no
    SRC_ATTRS = MethodDesignation,MethodTypeCode,MethodTypeName,WasteTransferID,WasteTransferMethodUsedID
    -> StringReplacer_14
StringReplacer_14
    FIND_TEXT = "\t"
    NO_MATCH = _FME_NO_OP_
    REPLACE_TEXT = " "
    REGEXP = no
    CASE = no
    SRC_ATTRS = MethodDesignation,MethodTypeCode,MethodTypeName,WasteTransferID,WasteTransferMethodUsedID
    -> WASTETRANSFERMETHODUSED (writer CSV_1)
WASTETRANSFERMETHODUSED (writer CSV_1)
    attributes: WasteTransferMethodUsedID int, WasteTransferID int, MethodTypeCode text, MethodTypeName text, MethodDesignation text
