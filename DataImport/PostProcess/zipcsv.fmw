FME workspace zipcsv.fmw

Parameters:
- SourceDataset_PATH = S:\Temp\EPRTR\Acces\CSV   # Source Folder and File Pathnames Folder
- DestZIP = S:\Temp\EPRTR\Acces\CSV\tururu.zip   # Destination ZIP file

Readers:
- PATH_1: PATH from $(SourceDataset_PATH)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> ZipArchiver
ZipArchiver
    DEL_FILE = No
    FILE_PATH = @Value(path_windows)
    ZIP_PATH = $(DestZIP)

FME custom transformer ZipArchiver
Compresses a file and appends it into the specified zip file.
    The archive name will become the same as the target file name. If a file having the same name as the target file has been archived in the zip file already, the target file will not be archived.
    The transformer creates a new zip file when receiving the first file that should be archived into it, if the specified zip file doesn't exist. 
    -----
    Note: Currently this transformer DOES NOT SUPPORT file path strings containing Non-ASCII characters.
    Unexpected result may occur if the target file path and/or zip file path contain Non-ASCII characters.
    -----
    Input features will be output from the Output port as-is.
    The transformer creates log features which contain these attributes for each file, and outputs them from the LogSuccess/LogFailure port.
    - Result: "success" if the file was archived successfully, "failure" otherwise.
    - Target File: the target file path.
    - Zip File: the zip file path.
    - Archive Name: the archive name of the target file in the zip file if archived successfully, empty otherwise.
    - Comment: compression ratio if archived successfully, failure reason otherwise.
    ファイルを圧縮し、指定したzipファイルに追加します。
    アーカイブ名は対象のファイル名と同じになります。対象とするファイルと同じ名前のファイルがすでにzipファイルにアーカイブされていた場合、その対象ファイルはアーカイブされません。
    指定したzipファイルが存在しない場合、このトランスフォーマーはそれにアーカイブすべき最初のファイルを受け取ったときに新しいzipファイルを作成します。
-----
    注：現在このトランスフォーマーは、非ASCII文字（半角の英数字・記号以外の文字）を含むファイルパス文字列をサポートしていません。
    対象ファイルパスおよび/またはzipファイルパスに非ASCII文字が含まれている場合、予期しない結果が生じることがあります。
-----
    入力フィーチャーはそのままOutputポートから出力されます。
    このトランスフォーマーは、次の属性を持つログフィーチャーをファイルごとに作成し、LogSuccess/LogFailureポートから出力します。
    - Result: ファイルが正常にアーカイブされた場合は"succcess"、そうでない場合は"failure"
    - Target File: 対象のファイルパス
    - Zip File: zipファイルパス
    - Archive Name: アーカイブに成功した場合はzipファイル内でのアーカイブ名、失敗した場合は空文字列
    - Comment: アーカイブに成功した場合は圧縮率、失敗した場合はその理由
Parameters 
    Target File: 
    Specify a file path that should be archived. You can also set a feature attribute value to this parameter.
    If you specify a folder path here, all files under the folder will be archived. In the case, the original directory structure will also be preserved, and the archive name of the file will contain path starting from the specified folder.
    アーカイブするファイルパスを指定します。フィーチャーの属性をこのパラメーターに設定することもできます。 
    ここにフォルダのパスを指定した場合は、そのフォルダ以下にある全てのファイルがアーカイブされます。その場合、元のディレクトリ構造も維持され、ファイルのアーカイブ名には、指定されたフォルダから始まるパスが含まれます。
    Zip File: 
    Specify a zip file path (*.zip). You can also set a feature attribute value to this parameter.
    If the extension of the specified file path is not "zip", the transformer will add ".zip" to the path automatically. 
    zipファイルパス（*.zip）を指定します。フィーチャーの属性をこのパラメーターに設定することもできます。 
    指定されたパスの拡張子が"zip"でない場合は、そのパスに".zip"を自動的に付加します。
    Delete Target File If Archived:
    Note: This parameter is not available currently.
    By default, the transformer will not touch the target file, but op
    tionally you can delete it after archiving by setting "Yes" to this parameter. 
    But the file that was failed to be archived will not be deleted anyway.
注：現在このパラメーターは使用できません。
    デフォルトでは、このトランスフォーマーは元のファイルに何らかの処理を加えることはありませんが、必要に応じて、このパラメーターを"Yes"に設定することによりアーカイブした後に削除することができます。
    ただし、アーカイブに失敗したファイルが削除されることはありません。
Copyright (c) 2015 pragmatica inc. 
    Permission is granted to anyone, free of charge, to use, modify and distribute the object code form of this transformer for any purpose, subject to the following restrictions: 
    1) The origin of this transformer and associated FME(R) software must not be misrepresented. 
    2) This transformer may only be used in conjunction with a validly licensed copy of FME software. 
    THIS SOFTWARE IS PROVIDED BY PRAGMATICA INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL PRAGMATICA INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- FILE_PATH =   # Target File
- ZIP_PATH =   # Zip File
- DEL_FILE = No   # Delete Target File If Archived

Input (input)
    -> ParameterFetcher
ParameterFetcher
    ATTR_LIST = __ziparchiver.filepath {$(FILE_PATH)} __ziparchiver.zippath {$(ZIP_PATH)} __ziparchiver.delfile {$(DEL_FILE)}
    -> TclCaller
TclCaller
    SRC:
      proc cleanPathAndMakeDir {} {
          proc cleanPath {attrName} {
              set path [string trimright [string map [list "\\" "/"] [FME_GetAttribute $attrName]] {/}]
              set path [regsub -all {/{2,}} $path {/}]
              FME_SetAttribute $attrName $path
              return $path
          }
          cleanPath "__ziparchiver.filepath"
          set zpath [cleanPath "__ziparchiver.zippath"]
          if {![regexp -nocase -- {\.zip$} $zpath]} {
              FME_SetAttribute "__ziparchiver.zippath" [set zpath  [format {%s.zip} $zpath]]
          }
          set dir [file dirname $zpath]
          return [expr [file exists $dir] || ![catch {file mkdir $dir}]]
      }
    VAL_ATTR = __ziparchiver.valid
    TCLPROG = cleanPathAndMakeDir
    -> PythonCaller
PythonCaller
    PYTHONSOURCE:
      import fme
      import fmeobjects
      import os, zipfile

      # 2015-05-24  Takashi Iijima  Original Implementation
      # Note: It doesn't support file path strings containing Non-ASCII characters.
      class ZipArchiver(object):
          def __init__(self):
              self.logger = fmeobjects.FMELogFile()

          def archive(self, fpath, aname):
              if os.path.isdir(fpath):
                  for sub in os.listdir(fpath):
                      self.archive('%s/%s' % (fpath, sub), '%s/%s' % (aname, sub))
                  try:
                      info = self.zipper.getinfo(aname)
                  except:
                      self.zipper.write(fpath, aname)
              elif fpath.lower() != self.zpath_lower:
                  result, msg = False, ''
                  if os.path.isfile(fpath):
                      try:
                          try:
                              info = self.zipper.getinfo(aname)
                              msg = '"%s" exists in the archive already.' % aname
                          except:
                              into = None
                              self.zipper.write(fpath, aname)
                              info = self.zipper.getinfo(aname)
                              after = info.compress_size/1024.0
                              before = info.file_size/1024.0
                              msg = '%.1f%% (%.1f/%.1fKB)' % (after/before*100.0, after, before)
                              '''
                              if self.delfile:
                                  try:
                                      os.remove(fpath)
                                  except:
                                      pass
                              '''
                              result = True
                      except Exception as ex:
                          msg = '%s' % ex
                  else:
                      msg = '"%s" does not exist or is not a file.' % fpath
                  self.outputLog(result, fpath, aname, msg)

          # Create and output Log feature.
          def outputLog(self, result, fpath, aname, msg):
              if result == False:
                  self.logger.logMessageString('ZipArchiver: %s' % msg, fmeobjects.FME_WARN)
              log = fmeobjects.FMEFeature()
              log.setAttribute('__ziparchiver.result', 'success' if result else 'failure')
              log.setAttribute('Target File', fpath)
              log.setAttribute('Zip File', self.zpath)
              log.setAttribute('Archive Name', aname if result else '')
              log.setAttribute('Comment', msg)
              log.setAttribute('fme_feature_type', 'ZipArchiver_%s' % ('Success' if result else 'Failure'))
              self.pyoutput(log)

          def input(self, feature):
              fpath = feature.getAttribute('__ziparchiver.filepath')
              basename = os.path.basename(fpath)
              self.zpath = feature.getAttribute('__ziparchiver.zippath')
              self.zpath_lower = self.zpath.lower()
              self.delfile = (feature.getAttribute('__ziparchiver.delfile') == 'Yes')
              self.zipper = None
              try:
                  self.zipper = zipfile.ZipFile(self.zpath, 'a', zipfile.ZIP_DEFLATED)
                  self.archive(fpath, basename)
              except Exception as ex:
                  self.outputLog(False, fpath, '', '%s' % ex)
              finally:
                  if self.zipper:
                      self.zipper.close()
              self.pyoutput(feature)

          def close(self):
              pass
    PYTHONSYMBOL = ZipArchiver
    NEW_ATTRIBUTES = __ziparchiver.result
    -> Tester
Tester
    TEST_MODE = Automatic
    TEST_CLAUSE = TEST __ziparchiver.result ATTRIBUTE_IS_MISSING ""
    TEST_DESCRIPTION = ""
    BOOL_OP = OR
    PASSED -> AttributeRemover
    FAILED -> AttributeRenamer
AttributeRemover
    REMOVE_ATTRS = __ziparchiver.filepath,__ziparchiver.result,__ziparchiver.valid,__ziparchiver.zippath,__ziparchiver.delfile
    -> Output (output)
Output (output)
AttributeRenamer
    ATTR_LIST = __ziparchiver.result,Result,
    -> AttributeExposer
AttributeExposer
    ATTR_LIST = "Target File","Zip File","Archive Name",Comment
    -> Tester_2
Tester_2
    TEST_MODE = Automatic
    TEST_CLAUSE = TEST @Value(Result) = success
    TEST_DESCRIPTION = ""
    BOOL_OP = OR
    PASSED -> AttributeKeeper
    FAILED -> AttributeKeeper_2
AttributeKeeper
    KEEP_ATTRS = Comment,Result,Target File,Zip File,Archive Name
    -> LogSuccess (output)
LogSuccess (output)
AttributeKeeper_2
    KEEP_ATTRS = Comment,Result,Target File,Zip File,Archive Name
    -> LogFailure (output)
LogFailure (output)
