FME workspace LCPandEPRTR_EXTRACT_DATA_ENVELOPE.fmw
Title: Extract_data_Envelope_xml
Description: Extract data inside Envelope xml.
History: 2016-01-25,yoly carrasco,v.1.

Parameters:
- Search_url = http://cdrtest.eionet.europa.eu/xml_recent_etc?RA_ID=720   # Search Url
- password =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   # pasword
- user = sa
- server = eeapc8235   # Server
- database = EPRTRlcp   # Database

Readers:
- MSSQL_ADO_1: MSSQL_ADO from $(database)

Creator_2
    GEOMTYPE = Geometry Object
    NUM = 1
    CREATED -> TimeStamper
TimeStamper
    FMT = ^Y-^m-^d ^H:^M:^S
    TIME_ATTR = _timestamp
    -> Tester_user_pass
AttributeCreator_2
    ATTR_LIST = description_env,@Value(description),coverage_env,@Value(coverage),obligation_env,@Value(obligation),title_env,@Value(title),year_env,@Value(year)
    -> FeatureMerger [input 1]
XMLFragmenter_Fragments: Inspector [off]
FeatureMerger
    ATTR_CONFLICT_RES = Use Requestor
    JOIN_KEYS = @Value(result.url) @Value(envelopeLink) AUTO @Value(result.country_code) @Value(countryCode) AUTO
    IGNORE_NULLS = No
    SUPPLIERS_FIRST = No
    ATTR_ACCUM_MODE = Merge Supplier
    PROCESS_DUPS = No
    MERGE_TYPE = Attributes Only
    NOT_MERGED -> SQLExecutor_Insert
    MERGED -> SQLExecutor_Update
    NOT_MERGED -> FeatureMerger_NotMerged
SQLExecutor_Update
    MSSQL_ADO_ENCRYPT_CONNECTION = NO
    MSSQL_ADO_QUERY_FEATURE_TYPES_FOR_MERGE_FILTERS = Yes
    SQL_STATEMENT:
      FME_SQL_DELIMITER ;
      BEGIN TRANSACTION
      begin try
      UPDATE [dbo].[Envelope_Import]
                 SET
                 	[title] = '@Value(result.title)'
                  ,[description] = '@Value(description)'
                  ,[reportingdate] = '@Value(result.reportingdate)'
                  ,[coverage] = '@Value(coverage)'
                  ,[countryCode] = '@Value(result.country_code)'
                  ,[obligation] = '@Value(obligation)'
                  ,[envelopeLink] = '@Value(result.url)'
                  ,[reportedYear] = '@Value(year_env)'
                  ,[endYear] = '@Value(result.endyear)'
                  ,[partOfYear] = '@Value(result.partofyear)'
                  ,[importDate] = '@Value(_timestamp)'
                  ,[processed] = @Value(processed)
                  ,[countryName] ='@Value(result.country_name)'
                  ,[locality] = '@Value(result.locality)'
                  ,[startyear] = '@Value(result.startyear)'
                  ,[lastworkitem] = '@Value(result.lastworkitem)'
                  ,[penultimateworkitem] = '@Value(result.penultimateworkitem)'
                  ,[creator] = '@Value(result.creator)'
                  ,[feedbacks] = '@Value(result.feedbacks)'
                  ,[envelopeID] = '@Value(result.id)'
                  ,[released] = @Value(result.released)
                  ,[blockedByQA] = @Value(result.blockedByQA)
                  ,[fileName] = '@Value(file.name)'

           Where envelopeImportID = @Value(envelopeImportID)

       commit TRANSACTION
          SELECT '' AS ErrorMessage2

      end try
      begin catch
      ROLLBACK TRANSACTION
      SELECT ERROR_MESSAGE() AS ErrorMessage2
      end catch;
    MSSQL_ADO_USE_SSPI = NO
    MSSQL_ADO_USER_NAME = $(user)
    EXPOSED_ATTRIBUTE_LIST = ErrorMessage2
    MSSQL_ADO_SERVER = $(server)
    MSSQL_ADO_PASSWORD = $(password)
    MSSQL_ADO_COMMAND_TIMEOUT = 30
    FORMAT = MSSQL_ADO
    DATASET = $(database)
    COMBINE_ATTRS = Keep Result Attributes if Conflict
    COMBINE_GEOM = Initiator Geometry Only
    RESULT -> Tester_2
Tester_2
    TEST_MODE = Automatic
    TEST_CLAUSE:
      TEST @Value(result.released) = 1
      TEST @Value(released) != @Value(result.released)
    TEST_DESCRIPTION = ""
    BOOL_OP = AND
    PASSED -> Tester
    FAILED -> Tester_2_Failed
Tester_2_Failed: Inspector
SQLExecutor_Insert
    MSSQL_ADO_ENCRYPT_CONNECTION = NO
    MSSQL_ADO_QUERY_FEATURE_TYPES_FOR_MERGE_FILTERS = Yes
    SQL_STATEMENT:
      FME_SQL_DELIMITER ;

      BEGIN TRANSACTION
      begin try
      INSERT INTO [dbo].[Envelope_Import]
                 ([title]
                  ,[description]
                  ,[reportingdate]
                  ,[coverage]
                  ,[countryCode]
                  ,[obligation]
                  ,[envelopeLink]
                  ,[reportedYear]
                  ,[endYear]
                  ,[partOfYear]
                  ,[importDate]
                  ,[processed]
                  ,[countryName]
                  ,[locality]
                  ,[startyear]
                  ,[lastworkitem]
                  ,[penultimateworkitem]
                  ,[creator]
                  ,[feedbacks]
                  ,[envelopeID]
                  ,[released]
                  ,[blockedByQA]
                  ,[fileName]
                  ,[reportID])
           VALUES
                 ('@Value(result.title)'
                 ,'@Value(description_env)'
                 ,'@Value(result.reportingdate)'
                 ,'@Value(coverage)'
                 ,'@Value(result.country_code)'
                 ,'@Value(obligation)'
                 ,'@Value(result.url)'
                 ,'@Value(year_env)'
                 ,'@Value(result.endyear)'
                 ,'@Value(result.partofyear)'
                 ,'@Value(_timestamp)'
                 ,0
                 ,'@Value(result.country_name)'
                 ,'@Value(result.locality)'
                 ,'@Value(result.startyear)'
                 ,'@Value(result.lastworkitem)'
                 ,'@Value(result.penultimateworkitem)'
                 ,'@Value(result.creator)'
                 ,'@Value(result.feedbacks)'
                 ,'@Value(result.id)'
                 ,@Value(result.released)
                 ,@Value(result.blockedByQA)
                 ,'@Value(file.name)'
                 ,NULL)

       commit TRANSACTION
       SELECT SCOPE_IDENTITY() AS envelopeImportID, '' As ErrorMessage2


      end try
      begin catch
      ROLLBACK TRANSACTION
      SELECT ERROR_MESSAGE() AS ErrorMessage2
      end catch;
    MSSQL_ADO_USE_SSPI = NO
    MSSQL_ADO_USER_NAME = $(user)
    EXPOSED_ATTRIBUTE_LIST = envelopeImportID,ErrorMessage2
    MSSQL_ADO_SERVER = $(server)
    MSSQL_ADO_PASSWORD = $(password)
    MSSQL_ADO_COMMAND_TIMEOUT = 30
    FORMAT = MSSQL_ADO
    DATASET = $(database)
    COMBINE_ATTRS = Keep Result Attributes if Conflict
    COMBINE_GEOM = Initiator Geometry Only
    RESULT -> Tester
Tester
    TEST_MODE = Automatic
    TEST_CLAUSE:
      TEST ErrorMessage2 NOT_ATTRIBUTE_VALUE_NULL ""
      TEST ErrorMessage2 NOT_ATTRIBUTE_IS_EMPTY ""
      TEST ErrorMessage2 NOT_ATTRIBUTE_IS_MISSING ""
    TEST_DESCRIPTION = ""
    BOOL_OP = AND
    FAILED -> Tester_3
Tester_3
    TEST_MODE = Automatic
    TEST_CLAUSE = TEST @Value(result.released) = 1
    TEST_DESCRIPTION = ""
    BOOL_OP = OR
    PASSED -> AttributeRemover
AttributeRemover
    LIST_ATTRS = _headers{} _headers{}.name _headers{}.value
    REMOVE_ATTRS = _response_body,xml_id,xml_matched_element,xml_parent_child_pos,xml_parent_id
    -> XMLFragmenter_2
Tester_4_Failed: Logger
    MESSAGE = Feature is:
    MAXCOORDS = 20
    MAXFEATS = 20
FeatureMerger_NotMerged: Inspector [off]

Bookmark: SEARCH ENVELOPES (urls)
Tester_user_pass
    CDRTEST_userXML = reporter
    CDRTEST_passXML =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
    source_xml = $(Search_url)
    CDR_userXML = tellealb
    CDR_passXML =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
    CDRSANDBOX_userXML = datareporter
    CDRSANDBOX_passXML =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
    AttributeCreator_Output -> HTTPCaller
HTTPCaller
    CONNECTION_TIMEOUT_LENGTH = 60
    VERIFY_SSL_CERTIFICATES = Yes
    AUTH_METHOD = Basic
    TARGET_ATTR = _response_body
    HTTP_METHOD = GET
    AUTH_PASSWORD = @Value(passFile)
    STATUS_CODE_ATTR = _http_status_code
    AUTH_USERNAME = @Value(userFile)
    TARGET_URL = $(Search_url)
    USE_COOKIES = No
    RESPONSE_HEADER_LIST_ATTR = _headers
    TRANSFER_TIMEOUT_LENGTH = 90
    FOLLOW_REDIRECTS = Yes
    ERROR_ATTR = _error
    SAVE_FILE = Attribute
    TARGET_ATTR_ENCODING = auto-detect
    -> XMLValidator
XMLValidator
    XML_INPUT_TYPE = Attribute Specifying XML Text
    LIST_NAME = _xml_error
    VAL_MODE_1 = Syntax Only
    XML_ATTR_TEXT = _response_body
    LIMIT_ERRORS = No
    PASSED -> XMLFlattener
XMLFlattener
    XML_SOURCE_TYPE = Attribute with XML document
    ATTRIBUTE_XML = _response_body
    EMBEDDED_EXPRESSIONS = results
    FLATTEN_OPTIONS = <structure separator="." map-empty-elements="yes" matched-prefix="attributes" matched-attributes="yes" cardinality="+{?}" structure-prefix="" child-position-attribute="" except-expression="" ui-mode="basic" matched-ancestor-attributes=""/>
    -> XMLFragmenter
XMLFragmenter
    XML_SOURCE_TYPE = Attribute with XML document
    ATTRIBUTE_XML = _response_body
    EMBEDDED_EXPRESSIONS = result
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = result.reportingdate result.lastworkitem result.startyear result.blockedByQA result.title result.url result.locality result.partofyear result.released result.endyear result.country_code result.country_name result.penultimateworkitem result.dataflow_uris result.creator result.id result.files result.dataflow_uris result.feedbacks
    FRAGMENTS -> HTTPCaller_2
    FRAGMENTS -> XMLFragmenter_Fragments

Bookmark: Envelopè Description Data
HTTPCaller_2
    CONNECTION_TIMEOUT_LENGTH = 60
    VERIFY_SSL_CERTIFICATES = Yes
    AUTH_METHOD = Basic
    TARGET_ATTR = xmlEnvelope
    HTTP_METHOD = GET
    AUTH_PASSWORD = @Value(passFile)
    STATUS_CODE_ATTR = _http_status_code
    AUTH_USERNAME = @Value(userFile)
    TARGET_URL = @Value(result.url)/xml
    USE_COOKIES = No
    RESPONSE_HEADER_LIST_ATTR = _headers
    TRANSFER_TIMEOUT_LENGTH = 90
    FOLLOW_REDIRECTS = Yes
    ERROR_ATTR = _error
    SAVE_FILE = Attribute
    TARGET_ATTR_ENCODING = auto-detect
    -> XMLFlattener_2
XMLFlattener_2
    XML_SOURCE_TYPE = Attribute with XML document
    ATTRIBUTE_XML = xmlEnvelope
    EMBEDDED_EXPRESSIONS = envelope
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = description title coverage obligation year
    -> AttributeCreator
AttributeCreator
    ATTR_LIST = xmlFile,@Value(xmlEnvelope)
    -> XMLFlattener_3
XMLFlattener_3
    XML_SOURCE_TYPE = Attribute with XML document
    ATTRIBUTE_XML = xmlFile
    EMBEDDED_EXPRESSIONS = file
    FLATTEN_OPTIONS = <structure separator="." map-empty-elements="yes" matched-prefix="attributes" matched-attributes="yes" cardinality="+{?}" structure-prefix="" child-position-attribute="" except-expression="" ui-mode="basic" matched-ancestor-attributes=""/>
    -> XMLFragmenter_3
XMLFragmenter_3
    XML_SOURCE_TYPE = Attribute with XML document
    ATTRIBUTE_XML = xmlFile
    EMBEDDED_EXPRESSIONS = file
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = file.link file.name file.uploaded file.restricted file.schema file.title file.type
    FRAGMENTS -> DateFormatter
DateFormatter
    SRCFMT = %Y-%m-%dT%H:%M:%SZ
    FMT = %Y-%m-%d %H:%M:%S
    INVALID_DATE_VALUE = null
    DATE_ATTR = result.reportingdate
    -> StringReplacer_2
StringReplacer_2
    SRC_ATTRS = result.feedbacks
    FIND_TEXT = \[|\]|'
    REGEXP = yes
    CASE = no
    NO_MATCH = _FME_NO_OP_
    -> StringReplacer
StringReplacer
    SRC_ATTRS = description
    REPLACE_TEXT = ''
    FIND_TEXT = '
    REGEXP = no
    CASE = no
    NO_MATCH = _FME_NO_OP_
    -> NullAttributeMapper
NullAttributeMapper
    OTHER_VALUE = False
    SOURCE_ATTR_VAL = Null Empty "Missing (Selected Attributes Only)"
    ATTRLIST = result.blockedByQA
    NEW_VALUE = 0
    NULL_TREATMENT = New Value
    ATTRCHOICE = Selected Attributes
    -> NullAttributeMapper_2
NullAttributeMapper_2
    OTHER_VALUE = True
    ATTRLIST = result.blockedByQA
    NEW_VALUE = 1
    NULL_TREATMENT = New Value
    ATTRCHOICE = Selected Attributes
    -> AttributeCreator_2

Bookmark: ENVELOPE_TEST
dbo.Envelope_Import (reader MSSQL_ADO_1)
    attributes: envelopeImportID bigint, title nvarchar(255), description ntext, reportingdate datetime, coverage nvarchar(255), countryCode nvarchar(2), obligation nvarchar(255), envelopeLink nvarchar(255), reportedYear nvarchar(4), endYear nvarchar(4), partOfYear nvarchar(255), importDate datetime, processed smallint, countryName nvarchar(100), locality nvarchar(100), startyear nvarchar(4), blockedByQA smalldatetime, lastworkitem nvarchar(50), penultimateworkitem nvarchar(50), released smalldatetime, creator nvarchar(255), feedbacks ntext
    -> FeatureMerger [input 2]

Bookmark: Data Xml file
XMLFragmenter_2
    XML_SOURCE_TYPE = Attribute with XML document
    ATTRIBUTE_XML = xmlEnvelope
    EMBEDDED_EXPRESSIONS = file
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = file.link file.schema file.name
    FRAGMENTS -> Tester_4
Tester_4
    TEST_MODE = Automatic
    TEST_CLAUSE:
      TEST file.schema NOT_ATTRIBUTE_IS_EMPTY ""
      TEST file.schema NOT_ATTRIBUTE_VALUE_NULL ""
      TEST file.schema NOT_ATTRIBUTE_IS_MISSING ""
    TEST_DESCRIPTION = ""
    BOOL_OP = AND
    PASSED -> TestFilter
    PASSED -> Tester_4_Failed
    PASSED -> Tester_4_Passed

Bookmark: Call the process by schema
TestFilter
    TEST_LIST = BOOL_OP,OR,COMPOSITE_TEST,<Unused>,TEST_CLAUSE,"TEST @UpperCase(@Value(file.schema)) CONTAINS LCPANDPRTRMAIN.XSD",LCPandEPRTRMain
    DEFAULT_VALUE = ERROR
    LCPandEPRTRMain -> FMEServerJobSubmitter
FMEServerJobSubmitter
    WORKSPACE_NAME = E-prtandLCP_Load_BBDD.fmw
    SERVER_NAME = fme.discomap.eea.europa.eu/fmeserver/repositories
    PASSWORD =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
    REPOSITORY = E-PRTRandLCP
    DATASET_OVERRIDE = NO
    SERVER_PORT = 0
    PRIORITY = 100
    SUBSECTION = SERVER_JOB_SUBMITTER
    BLOCKING = No
    WORKSPACE_PARAMETERS = SourceDataset_XML,@Value(file.link),IDEnvelope,@Value(envelopeImportID)
    USERNAME = telletxea
Tester_4_Passed: Inspector
