FME workspace E-prtandLCP_Load_BBDD.fmw
Title: E-prtandLCP_Load_BBDD
Description: Process to write a XML in a SQL database.
Requirements: 1 XML
History: 12/02/2016,Ander Carrasco Aretxaga,Version 1.0

Parameters:
- SourceDataset_XML = http://cdrtest.eionet.europa.eu/at/eu/eprtr_lcp/envvsf6_a/LCPandPRTRMainNew.xml   # Source XML File(s)
- IDEnvelope = 17
- Database = EPRTRlcp
- Server = eeapc8235
- User = sa
- Password =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

Creator
    GEOMTYPE = Geometry Object
    NUM = 1
    CREATED -> ParameterFetcher
ParameterFetcher
    ATTR_LIST = _source_xml {$(SourceDataset_XML)} _Server {$(Server)} _User {$(User)} _Password {$(Password)} _Database {$(Database)} _IDEnvelope {$(IDEnvelope)}
    -> TimeStamper
TimeStamper
    FMT = ^Y-^m-^d ^H:^M:^S
    TIME_ATTR = _timestamp
    -> TimeStamper_2
AttributeFileReader
    FILE_NAME = @Value(file)
    DEST_ATTR = _file_contents
    CHAR_ENCODING = utf-8
    -> StringReplacer_5
StringReplacer_5
    SRC_ATTRS = _file_contents
    FIND_TEXT = '
    REGEXP = no
    REPLACE_TEXT = ''
    NO_MATCH = _FME_NO_OP_
    CASE = no
    -> SchemaName_LCPandPRTR
SchemaName_LCPandPRTR: AttributeCreator
    ATTR_LIST = schemaName,LCPandPRTR
    -> XMLValidator_2
SQLExecutor
    MSSQL_ADO_ENCRYPT_CONNECTION = NO
    SQL_STATEMENT:
      FME_SQL_DELIMITER ;
      begin try

      UPDATE [dbo].[Envelope_Import]
         SET [reportID] = @Value(reportID) WHERE envelopeImportID = @Value(_IDEnvelope)
         select '' as ErrorMessag
      end try
      begin catch
      SELECT ERROR_MESSAGE() AS ErrorMessag
      end catch;
    MSSQL_ADO_USER_NAME = $(User)
    DATASET = $(Database)
    COMBINE_ATTRS = Keep Result Attributes if Conflict
    MSSQL_ADO_COMMAND_TIMEOUT = 30
    MSSQL_ADO_SERVER = $(Server)
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD = $(Password)
    RESULT -> Tester
PlantReports: SQLExecutor
    MSSQL_ADO_ENCRYPT_CONNECTION = NO
    SQL_STATEMENT:
      FME_SQL_DELIMITER ;
      begin try

      INSERT INTO [dbo].[PlantReports]
                 ([reportID])
           VALUES
                 (@Value(reportID))
           SELECT SCOPE_IDENTITY() AS plantReportsID, '' AS ErrorMessag
      end try
      begin catch
      SELECT ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = plantReportsID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> Tester_2
Tester_2
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> FacilityReports
    PASSED -> Tester_ErrorMessage
FacilityReports: SQLExecutor
    MSSQL_ADO_ENCRYPT_CONNECTION = NO
    SQL_STATEMENT:
      FME_SQL_DELIMITER ;
      begin try
      INSERT INTO [dbo].[FacilityReports]
                 ([reportID])
           VALUES
                 (@Value(reportID))
           SELECT SCOPE_IDENTITY() AS FacilityReportsID, '' AS ErrorMessag
      end try
      begin catch
      SELECT ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = FacilityReportsID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> Tester_3
Tester_3
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    PASSED -> Tester_ErrorMessage
    FAILED -> AttributeRemover
AttributeRemover
    REMOVE_ATTRS = _creation_instance,_http_status_code,_source_xml,_timestamp,_timestamp_file,countryID,ErrorMessag,file,fileName,remarkText,reportingYear,schemaName,tableName,userFile,value
    LIST_ATTRS = _headers{} _headers{}.name _headers{}.value
    -> AttributeCreator
AttributeCreator
    ATTR_LIST = xmlPlantReports,@Value(_file_contents),xmlFacilityReports,@Value(_file_contents)
    -> Plantreports
    -> FacilityReport
Plantreports
    PLANTREPORTSID = @Value(plantReportsID)
    XMLPLANTREPORTS = @Value(xmlPlantReports)
    _FILE_CONTENTS = @Value(_file_contents)
    AttributeRemover_11_Output -> Tester_ErrorMessage
    AttributeRemover_9_Output -> Tester_ErrorMessage
    AttributeRemover__Output -> Tester_ErrorMessage
    AttributeRemover_7_Output -> Tester_ErrorMessage
    AttributeRemover_15_Output -> Tester_ErrorMessage
    AttributeRemover_14_Output -> Tester_ErrorMessage
FacilityReport
    XMLFACILITYREPORTS = @Value(xmlFacilityReports)
    FACILITYREPORTSID = @Value(FacilityReportsID)
    _FILE_CONTENTS = @Value(_file_contents)
    Tester_4_Passed -> Tester_ErrorMessage
    SQLExecutor_2_Result -> Tester_ErrorMessage
    SQLExecutor_3_Initiator -> Tester_ErrorMessage
    SQLExecutor_5_Initiator -> Tester_ErrorMessage
    SQLExecutor_4_Result -> Tester_ErrorMessage
    SQLExecutor_3_Initiator_2 -> Tester_ErrorMessage
Tester_ErrorMessage
    TEST_DESCRIPTION = ""
    TEST_MODE = Automatic
    TEST_CLAUSE:
      TEST ErrorMessage NOT_ATTRIBUTE_IS_EMPTY ""
      TEST ErrorMessage NOT_ATTRIBUTE_VALUE_NULL ""
      TEST ErrorMessage NOT_ATTRIBUTE_IS_MISSING ""
    BOOL_OP = AND
    PASSED -> NullAttributeMapper
    FAILED -> SQLExecutor_2
NullAttributeMapper
    NULL_TREATMENT = New Value
    ATTRLIST = reportID
    NEW_VALUE = Null
    SOURCE_ATTR_VAL = Empty "Missing (Selected Attributes Only)" Null
    ATTRCHOICE = Selected Attributes
    -> StringReplacer_DESC_Message
StringReplacer_DESC_Message
    SRC_ATTRS = ErrorMessag
    FIND_TEXT = '
    REGEXP = no
    REPLACE_TEXT = ''
    NO_MATCH = _FME_NO_OP_
    CASE = no
    -> IMPORT_ERRORS
IMPORT_ERRORS: SQLExecutor
    MSSQL_ADO_ENCRYPT_CONNECTION = NO
    SQL_STATEMENT:
      SET QUOTED_IDENTIFIER OFF;
      INSERT INTO [dbo].[IMPORT_ERRORS]
                 ([envelopeImportID]
                 ,[importID]
                 ,[table]
                 ,[message]
                 ,[raisedAt])
           VALUES
                 (@Value(_IDEnvelope)
                 ,@Value(reportID)
                 ,'@Value(tableName)'
                 ,'@Value(ErrorMessag)'
                 ,'@Value(_timestamp)');
      SET QUOTED_IDENTIFIER ON;
    MSSQL_ADO_USER_NAME = @Value(_User)
    DATASET = @Value(_Database)
    COMBINE_ATTRS = Result Attributes Only
    MSSQL_ADO_COMMAND_TIMEOUT = 30
    MSSQL_ADO_SERVER = @Value(_Server)
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD = @Value(_Password)
    INITIATOR -> IMPORT_ERRORS_Result
IMPORT_ERRORS_Result: Inspector
SQLExecutor_2
    MSSQL_ADO_ENCRYPT_CONNECTION = NO
    SQL_STATEMENT:
      FME_SQL_DELIMITER ;
      begin try

      UPDATE [dbo].[Envelope_Import]
         SET [processed] = 1 WHERE envelopeImportID = @Value(_IDEnvelope)

      end try
      begin catch
      SELECT ERROR_MESSAGE() AS ErrorMessag
      end catch;
    MSSQL_ADO_USER_NAME = $(User)
    DATASET = $(Database)
    COMBINE_ATTRS = Keep Result Attributes if Conflict
    MSSQL_ADO_COMMAND_TIMEOUT = 30
    MSSQL_ADO_SERVER = $(Server)
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD = $(Password)
HTTPCaller_2__Rejected_: Logger
    MAXFEATS = 20
    MAXCOORDS = 20
    MESSAGE = Feature is:
    LOGGED -> Inspector
Inspector [off]
AttributeCreator_17_Output: Inspector [off]

Bookmark: Create temporal File
TimeStamper_2
    FMT = FME Date/Time (^Y^m^d^H^M^S)
    TIME_ATTR = _timestamp_file
    -> AttributeCreator_17
AttributeCreator_17
    ATTR_LIST = file,c:\temp\@Value(_timestamp_file)_YOLI.xml,fileName,@Value(_source_xml)
    -> AttributeCreator_17_Output
    -> Tester_user_pass
Tester_user_pass
    CDRSANDBOX_userXML = datareporter
    source_xml = @Value(_source_xml)
    CDRSANDBOX_passXML =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
    CDR_userXML = tellealb
    CDR_passXML =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
    CDRTEST_userXML = reporter
    CDRTEST_passXML =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
    AttributeCreator_Output -> HTTPCaller_2
HTTPCaller_2
    VERIFY_SSL_CERTIFICATES = Yes
    TARGET_URL = @Value(_source_xml)
    AUTH_METHOD = Basic
    HTTP_METHOD = GET
    FOLLOW_REDIRECTS = Yes
    CONNECTION_TIMEOUT_LENGTH = 60
    SAVE_FILE = File
    ERROR_ATTR = _error
    RESPONSE_HEADER_LIST_ATTR = _headers
    USE_COOKIES = No
    OUTPUT_FILENAME = @Value(file)
    AUTH_USERNAME = @Value(userFile)
    TRANSFER_TIMEOUT_LENGTH = 90
    STATUS_CODE_ATTR = _http_status_code
    FILE_PATH_ATTR = file
    SAVE_MULTI = No
    AUTH_PASSWORD = @Value(passFile)
    -> AttributeFileReader
    <Rejected> -> HTTPCaller_2__Rejected_

Bookmark: VALIDATE Syntax
XMLValidator_2
    XML_ATTR_TEXT = _file_contents
    XML_INPUT_TYPE = Attribute Specifying XML Text
    LIMIT_ERRORS = No
    VAL_MODE_1 = Syntax Only
    LIST_NAME = _xml_error
    PASSED -> XMLFlattener
    FAILED -> NullAttributeMapper

Bookmark: LCPandPRTR
XMLFlattener
    NEW_ATTRIBUTES = countryID remarkText reportingYear
    EMBEDDED_EXPRESSIONS = LCPandPRTR
    XML_SOURCE_TYPE = Attribute with XML document
    ATTRIBUTE_XML = _file_contents
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> FeatureReader
FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_CountryCodeType
    MSSQL_ADO_USE_SSPI = NO
    WHERE = value = '@Value(countryID)'
    MSSQL_ADO_USER_NAME = sa
    MSSQL_ADO_QUERY_FEATURE_TYPES_FOR_MERGE_FILTERS = Yes
    COMBINE_GEOM = Use Result
    MSSQL_ADO_COMMAND_TIMEOUT = 30
    MSSQL_ADO_ENCRYPT_CONNECTION = NO
    ATTRIBUTES = dbo.Common_CountryCodeType,"value,id"
    dbo.Common_CountryCodeType -> Report
Report: SQLExecutor
    MSSQL_ADO_ENCRYPT_CONNECTION = NO
    SQL_STATEMENT:
      FME_SQL_DELIMITER ;
      begin try

      INSERT INTO [dbo].[Report]
                 ([countryID]
                 ,[remarkText]
                 ,[reportingYear])
           VALUES
                 (@Value(id)
                 ,'@Value(remarkText)'
                 ,@Value(reportingYear))
           SELECT SCOPE_IDENTITY() AS reportID, '' AS ErrorMessag
      end try
      begin catch
      SELECT ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = reportID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> SQLExecutor
Tester
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> PlantReports
    PASSED -> Tester_ErrorMessage

FME custom transformer ProductionVolume

Parameters:
- XMLPRODUCTIONVOLUME = @Value(xmlProductionVolume)   # xmlProductionVolume
- FACILITYREPORTID = @Value(FacilityReportID)   # FacilityReportID

Bookmark: PoductionVolume
XMLFlattener_ProductionVolume_2_Input (input)
    -> XMLFlattener_ProductionVolume_2
XMLFlattener_ProductionVolume_2
    EMBEDDED_EXPRESSIONS = ProductionVolume
    XML_SOURCE_TYPE = Attribute with XML document
    ATTRIBUTE_XML = xmlProductionVolume
    FLATTEN_OPTIONS = <structure separator="." map-empty-elements="yes" matched-prefix="attributes" matched-attributes="yes" cardinality="+{?}" structure-prefix="" child-position-attribute="" except-expression="" ui-mode="basic" matched-ancestor-attributes=""/>
    -> XMLFrag_ProductionVolume
XMLFrag_ProductionVolume: XMLFragmenter
    NEW_ATTRIBUTES = productName quantity
    EMBEDDED_EXPRESSIONS = ProductionVolume
    XML_SOURCE_TYPE = Attribute with XML document
    ATTRIBUTE_XML = xmlProductionVolume
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> AttributeCreator_3
AttributeCreator_3
    ATTR_LIST = xmlquantity,@Value(xml_fragment)
    -> XMLFlattener_quantity
ProductionVolume: SQLExecutor
    MSSQL_ADO_ENCRYPT_CONNECTION = NO
    SQL_STATEMENT:
      FME_SQL_DELIMITER ;
      DECLARE @quantityID int

      BEGIN TRANSACTION
      begin try
      INSERT INTO [dbo].[QuantityType]
                 ([Quantity]
                 ,[UnitCode])
           VALUES
                 (@Value(Quantitytquantity)
                 ,@Value(idUnitCodequantity))
      SET @quantityID = (SELECT SCOPE_IDENTITY())

      INSERT INTO [dbo].[ProductionVolume]
                 ([productName]
                 ,[quantity]
                 ,[facilityReportID])
           VALUES
                 ('@Value(productName)'
                 ,@quantityID
                 ,@Value(FacilityReportID))

       SELECT SCOPE_IDENTITY() AS plantTypeID, '' as ErrorMessag


       commit TRANSACTION


      end try
      begin catch
          ROLLBACK TRANSACTION
          SELECT 0 AS plantTypeID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = plantTypeID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> SQLExecutor_2_Result_1 (output)
SQLExecutor_2_Result_1 (output)

Bookmark: Quantity
XMLFlattener_quantity
    EMBEDDED_EXPRESSIONS = quantity
    XML_SOURCE_TYPE = Attribute with XML document
    ATTRIBUTE_XML = xmlquantity
    FLATTEN_OPTIONS = <structure separator="." map-empty-elements="yes" matched-prefix="attributes" matched-attributes="yes" cardinality="+{?}" structure-prefix="" child-position-attribute="" except-expression="" ui-mode="basic" matched-ancestor-attributes=""/>
    -> quantity
quantity: XMLFragmenter
    NEW_ATTRIBUTES = Quantity UnitCode
    EMBEDDED_EXPRESSIONS = quantity
    XML_SOURCE_TYPE = Attribute with XML document
    ATTRIBUTE_XML = xmlquantity
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_10
FeatureReader_10
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_UnitCodeType
    MSSQL_ADO_USE_SSPI = NO
    WHERE = value = '@Value(UnitCode)'
    MSSQL_ADO_USER_NAME = sa
    MSSQL_ADO_QUERY_FEATURE_TYPES_FOR_MERGE_FILTERS = Yes
    COMBINE_GEOM = Use Result
    MSSQL_ADO_COMMAND_TIMEOUT = 30
    MSSQL_ADO_ENCRYPT_CONNECTION = NO
    ATTRIBUTES = dbo.Common_UnitCodeType,"value,id"
    dbo.Common_UnitCodeType -> AttributeRenamer_10
AttributeRenamer_10
    ATTR_LIST = Quantity,Quantitytquantity,@Value(Quantity),id,idUnitCodequantity,@Value(id)
    -> ProductionVolume

FME custom transformer PlantType

Parameters:
- PLANTREPORTID = @Value(plantReportID)   # plantReportID
- XMLPLANTTYPE = @Value(xmlPlantType)   # xmlPlantType

XMLFlattener_PlantType_Input (input)
    -> XMLFla_PlantType

Bookmark: PlantType
XMLFla_PlantType: XMLFlattener
    EMBEDDED_EXPRESSIONS = PlantType
    XML_SOURCE_TYPE = Attribute with XML document
    ATTRIBUTE_XML = xmlPlantType
    FLATTEN_OPTIONS = <structure separator="." map-empty-elements="yes" matched-prefix="attributes" matched-attributes="yes" cardinality="+{?}" structure-prefix="" child-position-attribute="" except-expression="" ui-mode="basic" matched-ancestor-attributes=""/>
    -> AttributeRemover_8
AttributeRemover_8
    REMOVE_ATTRS = xml_fragment,xmlEnergy,xmlTotalEmisionToAir
    -> XMLFrag_PlantType
XMLFrag_PlantType: XMLFragmenter
    NEW_ATTRIBUTES = combustionPlantType
    EMBEDDED_EXPRESSIONS = PlantType
    XML_SOURCE_TYPE = Attribute with XML document
    ATTRIBUTE_XML = xmlPlantType
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> combustionPlantTypeFilterByValue
combustionPlantTypeFilterByValue: FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_CombustionType
    MSSQL_ADO_USE_SSPI = NO
    WHERE = value = '@Value(combustionPlantType)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_CombustionType,"value,id"
    dbo.Common_CombustionType -> Rename_ID_Value
Rename_ID_Value: AttributeRenamer
    ATTR_LIST = id,combustionPlantTypeValue,@Value(id)
    -> Rename_xml_Fragment
Rename_xml_Fragment: AttributeCreator
    ATTR_LIST = xmlthermalInput,@Value(xml_fragment)
    -> XMLFlat_thermalInput
XMLFlat_thermalInput: XMLFlattener
    EMBEDDED_EXPRESSIONS = thermalInput
    XML_SOURCE_TYPE = Attribute with XML document
    ATTRIBUTE_XML = xmlthermalInput
    FLATTEN_OPTIONS = <structure separator="." map-empty-elements="yes" matched-prefix="attributes" matched-attributes="yes" cardinality="+{?}" structure-prefix="" child-position-attribute="" except-expression="" ui-mode="basic" matched-ancestor-attributes=""/>
    -> XMLFrag_thermalInput
XMLFrag_thermalInput: XMLFragmenter
    NEW_ATTRIBUTES = Quantity UnitCode
    EMBEDDED_EXPRESSIONS = thermalInput
    XML_SOURCE_TYPE = Attribute with XML document
    ATTRIBUTE_XML = xmlthermalInput
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> UnitCodeFilterByValue
UnitCodeFilterByValue: FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_UnitCodeType
    MSSQL_ADO_USE_SSPI = NO
    WHERE = value = '@Value(UnitCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_UnitCodeType,"value,id"
    dbo.Common_UnitCodeType -> Rename_ID_Value_2
Rename_ID_Value_2: AttributeRenamer
    ATTR_LIST = Quantity,QuantitythermalInput,@Value(Quantity),id,idUnitCodethermalInput,@Value(id)
    -> PlantTypeQuantityType
PlantTypeQuantityType: SQLExecutor
    MSSQL_ADO_ENCRYPT_CONNECTION = NO
    SQL_STATEMENT:
      FME_SQL_DELIMITER ;
      DECLARE @thermalInputID int

      BEGIN TRANSACTION
      begin try
      INSERT INTO [dbo].[QuantityType]
                 ([Quantity]
                 ,[UnitCode])
           VALUES
                 (@Value(QuantitythermalInput)
                 ,@Value(idUnitCodethermalInput))
      SET @thermalInputID = (SELECT SCOPE_IDENTITY())

      INSERT INTO [dbo].[PlantType]
                 ([combustionPlantType]
                 ,[thermalInput]
                 ,[plantReportID])
           VALUES
                 (@Value(combustionPlantTypeValue)
                 ,@thermalInputID
                 ,@Value(plantReportID))

       SELECT SCOPE_IDENTITY() AS plantTypeID, '' as ErrorMessag


       commit TRANSACTION


      end try
      begin catch
          ROLLBACK TRANSACTION
          SELECT 0 AS plantTypeID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = plantTypeID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> ErrorTester
ErrorTester: Tester
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> AttributeRemover_9
AttributeRemover_9
    REMOVE_ATTRS = combustionPlantType,combustionPlantTypeValue,ErrorMessag,idUnitCodethermalInput,plantTypeID,QuantitythermalInput,UnitCode,xml_fragment,xml_id,xml_matched_element,xml_parent_child_pos,xml_parent_id,xmlPlantType,xmlthermalInput
    -> AttributeRemover_9_Output_2 (output)
AttributeRemover_9_Output_2 (output)

FME custom transformer IEDArt72

Parameters:
- XMLIEDART72 = @Value(xmlIEDArt72)   # xmlIEDArt72
- PLANTREPORTID = @Value(plantReportID)   # plantReportID
- SUBSTANTIALCHANGE = @Value(substantialChange)   # substantialChange
- XMLLCPDEROGATIONS = @Value(xmlLCPDerogations)   # xmlLCPDerogations

XMLFlattener_PlantType_3_Input (input)
    -> XMLFlattener_PlantType_3

Bookmark: IEDArt72
XMLFlattener_PlantType_3
    EMBEDDED_EXPRESSIONS = LCPDerogations
    XML_SOURCE_TYPE = Attribute with XML document
    ATTRIBUTE_XML = xmlLCPDerogations
    FLATTEN_OPTIONS = <structure separator="." map-empty-elements="yes" matched-prefix="attributes" matched-attributes="yes" cardinality="+{?}" structure-prefix="" child-position-attribute="" except-expression="" ui-mode="basic" matched-ancestor-attributes=""/>
    -> AttributeRemover_12
AttributeRemover_12
    REMOVE_ATTRS = xmlEnergy,xmlTotalEmisionToAir,xml_fragment
    -> IEDArt72
IEDArt72: XMLFragmenter
    NEW_ATTRIBUTES = iEDArt72_4a iEDArt72_4b remarkText
    EMBEDDED_EXPRESSIONS = IEDArt72
    XML_SOURCE_TYPE = Attribute with XML document
    ATTRIBUTE_XML = xmlIEDArt72
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> NullAttributeMapper_True
NullAttributeMapper_True
    OTHER_VALUE = true
    NULL_TREATMENT = New Value
    ATTRLIST = iEDArt72_4a iEDArt72_4b substantialChange
    NEW_VALUE = 1
    ATTRCHOICE = Selected Attributes
    -> NullAttributeMapper_False
NullAttributeMapper_False
    OTHER_VALUE = false
    NULL_TREATMENT = New Value
    ATTRLIST = iEDArt72_4a iEDArt72_4b substantialChange
    NEW_VALUE = 0
    ATTRCHOICE = Selected Attributes
    -> IEDArt72_2
IEDArt72_2: SQLExecutor
    MSSQL_ADO_ENCRYPT_CONNECTION = NO
    SQL_STATEMENT:
      FME_SQL_DELIMITER ;
      BEGIN TRANSACTION
      begin try

      INSERT INTO [dbo].[IEDArt72]
                 ([iEDArt72_4a]
                 ,[iEDArt72_4b]
                 ,[remarkText]
                 ,[plantReportID])
           VALUES
                 (@Value(iEDArt72_4a)
                 ,@Value(iEDArt72_4b)
                 ,'@Value(remarkText)'
                 ,@Value(plantReportID))

       SELECT SCOPE_IDENTITY() AS iEDArt72ID, '' as ErrorMessag


       commit TRANSACTION


      end try
      begin catch
          ROLLBACK TRANSACTION
          SELECT 0 AS iEDArt72ID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = iEDArt72ID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> ErrorTester_3
ErrorTester_3: Tester
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> AttributeRemover_13
    PASSED -> AttributeRemover_14_Output_3 (output)
AttributeRemover_14_Output_3 (output)
AttributeRemover_13
    REMOVE_ATTRS = iEDArt72_4a,iEDArt72_4b,remarkText,substantialChange,xml_id,xml_matched_element,xml_parent_child_pos,xml_parent_id,xmlFacilityReports,xmlLCPDerogations
    -> AttributeCreator_4
AttributeCreator_4
    ATTR_LIST = xmlDesulphurisationRate,@Value(xml_fragment),xmlSO2,@Value(xml_fragment)
    -> XMLFlattener_DesulphurisationRate
    -> XMLFlattener_DesulphurisationRate_2
XMLFlattener_DesulphurisationRate
    EMBEDDED_EXPRESSIONS = DesulphurisationRate
    XML_SOURCE_TYPE = Attribute with XML document
    ATTRIBUTE_XML = xmlDesulphurisationRate
    FLATTEN_OPTIONS = <structure separator="." map-empty-elements="yes" matched-prefix="attributes" matched-attributes="yes" cardinality="+{?}" structure-prefix="" child-position-attribute="" except-expression="" ui-mode="basic" matched-ancestor-attributes=""/>
    -> XMLFra_DesulphurisationRate
XMLFra_DesulphurisationRate: XMLFragmenter
    NEW_ATTRIBUTES = month quantity
    EMBEDDED_EXPRESSIONS = DesulphurisationRate
    XML_SOURCE_TYPE = Attribute with XML document
    ATTRIBUTE_XML = xmlDesulphurisationRate
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_12
FeatureReader_12
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_MonthType
    MSSQL_ADO_USE_SSPI = NO
    WHERE = value = '@Value(month)'
    MSSQL_ADO_USER_NAME = sa
    MSSQL_ADO_QUERY_FEATURE_TYPES_FOR_MERGE_FILTERS = Yes
    COMBINE_GEOM = Use Result
    MSSQL_ADO_COMMAND_TIMEOUT = 30
    MSSQL_ADO_ENCRYPT_CONNECTION = NO
    ATTRIBUTES = dbo.Common_MonthType,"value,id"
    dbo.Common_MonthType -> AttributeRenamer_12
AttributeRenamer_12
    ATTR_LIST = quantity,QuantityDesulphurisationRate,@Value(quantity),id,idDesulphurisationRateMonth,@Value(id)
    -> DesulphurisationRate
DesulphurisationRate: SQLExecutor
    MSSQL_ADO_ENCRYPT_CONNECTION = NO
    SQL_STATEMENT:
      FME_SQL_DELIMITER ;

      BEGIN TRANSACTION
      begin try
      INSERT INTO [dbo].[DesulphurisationRate]
                 ([month]
                 ,[quantity]
                 ,[iEDArt72ID])
           VALUES
                 (@Value(idDesulphurisationRateMonth)
                 ,@Value(QuantityDesulphurisationRate)
                 ,@Value(iEDArt72ID))

       SELECT SCOPE_IDENTITY() AS DesulphurisationRateID, '' as ErrorMessag


       commit TRANSACTION


      end try
      begin catch
          ROLLBACK TRANSACTION
          SELECT 0 AS DesulphurisationRateID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = DesulphurisationRateID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> ErrorTester_2
ErrorTester_2: Tester
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> AttributeRemover_14
AttributeRemover_14
    REMOVE_ATTRS = ErrorMessag,xml_fragment,xml_id,xml_matched_element,xml_parent_child_pos,xml_parent_id,xmlPlantType,DesulphurisationRateID,idDesulphurisationRateMonth,QuantityDesulphurisationRate,xmlDesulphurisationRate
    -> AttributeRemover_14_Output_2 (output)
AttributeRemover_14_Output_2 (output)
XMLFlattener_DesulphurisationRate_2
    EMBEDDED_EXPRESSIONS = SO2
    XML_SOURCE_TYPE = Attribute with XML document
    ATTRIBUTE_XML = xmlSO2
    FLATTEN_OPTIONS = <structure separator="." map-empty-elements="yes" matched-prefix="attributes" matched-attributes="yes" cardinality="+{?}" structure-prefix="" child-position-attribute="" except-expression="" ui-mode="basic" matched-ancestor-attributes=""/>
    -> XMLFrag_SO2
XMLFrag_SO2: XMLFragmenter
    NEW_ATTRIBUTES = month quantity
    EMBEDDED_EXPRESSIONS = SO2
    XML_SOURCE_TYPE = Attribute with XML document
    ATTRIBUTE_XML = xmlSO2
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_11
FeatureReader_11
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_MonthType
    MSSQL_ADO_USE_SSPI = NO
    WHERE = value = '@Value(month)'
    MSSQL_ADO_USER_NAME = sa
    MSSQL_ADO_QUERY_FEATURE_TYPES_FOR_MERGE_FILTERS = Yes
    COMBINE_GEOM = Use Result
    MSSQL_ADO_COMMAND_TIMEOUT = 30
    MSSQL_ADO_ENCRYPT_CONNECTION = NO
    ATTRIBUTES = dbo.Common_MonthType,"value,id"
    dbo.Common_MonthType -> AttributeRenamer_11
AttributeRenamer_11
    ATTR_LIST = quantity,QuantitySO2,@Value(quantity),id,idSO2,@Value(id)
    -> SO2
SO2: SQLExecutor
    MSSQL_ADO_ENCRYPT_CONNECTION = NO
    SQL_STATEMENT:
      FME_SQL_DELIMITER ;

      BEGIN TRANSACTION
      begin try
      INSERT INTO [dbo].[SO2]
                 ([month]
                 ,[quantity]
                 ,[iEDArt72ID])
           VALUES
                 (@Value(idSO2)
                 ,@Value(QuantitySO2)
                 ,@Value(iEDArt72ID))
      SELECT SCOPE_IDENTITY() AS SO2ID, '' as ErrorMessag
      commit TRANSACTION

      end try
      begin catch
          ROLLBACK TRANSACTION
          SELECT 0 AS SO2ID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = DesulphurisationRateID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> ErrorTester
ErrorTester: Tester
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> AttributeRemover_15
AttributeRemover_15
    REMOVE_ATTRS = ErrorMessag,xml_fragment,xml_id,xml_matched_element,xml_parent_child_pos,xml_parent_id,xmlPlantType,idSO2,QuantitySO2,xmlSO2
    -> AttributeRemover_15_Output_2 (output)
AttributeRemover_15_Output_2 (output)

FME custom transformer Plantreports

Parameters:
- XMLPLANTREPORTS = @Value(xmlPlantReports)   # xmlPlantReports
- PLANTREPORTSID = @Value(plantReportsID)   # plantReportsID
- _FILE_CONTENTS = @Value(_file_contents)   # File Contents

XMLFlattener_2_Input (input)
    -> XMLFlattener_2

Bookmark: Plantreports
XMLFlattener_2
    EMBEDDED_EXPRESSIONS = PlantReports
    XML_SOURCE_TYPE = Attribute with XML document
    ATTRIBUTE_XML = _file_contents
    FLATTEN_OPTIONS = <structure separator="." map-empty-elements="yes" matched-prefix="attributes" matched-attributes="yes" cardinality="+{?}" structure-prefix="" child-position-attribute="" except-expression="" ui-mode="basic" matched-ancestor-attributes=""/>
    -> XMLFragmenter
XMLFragmenter
    NEW_ATTRIBUTES = dBPlantId statusOfThePlant extensionBy50MWOrMore substantialChange dateOfStartOperation refineries operationHours remarkText
    EMBEDDED_EXPRESSIONS = PlantReport
    XML_SOURCE_TYPE = Attribute with XML document
    ATTRIBUTE_XML = xmlPlantReports
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> PlantReport_2
PlantReport_2
    DBPLANTID = @Value(dBPlantId)
    DATEOFSTARTOPERATION = @Value(dateOfStartOperation)
    XML_FRAGMENT = @Value(xml_fragment)
    PLANTREPORTSID = @Value(plantReportsID)
    REMARKTEXT = @Value(remarkText)
    REFINERIES = @Value(refineries)
    OPERATIONHOURS = @Value(operationHours)
    EXTENSIONBY50MWORMORE = @Value(extensionBy50MWOrMore)
    STATUSOFTHEPLANT = @Value(statusOfThePlant)
    SUBSTANTIALCHANGE = @Value(substantialChange)
    AttributeRemover__Output_1 -> AttributeRemover__Output (output)
    AttributeRemover_7_Output_1 -> AttributeRemover_7_Output (output)
    AttributeRemover_11_Output_1 -> AttributeRemover_11_Output (output)
    AttributeRemover_15_Output_1 -> AttributeRemover_15_Output (output)
    AttributeRemover_14_Output_1 -> AttributeRemover_14_Output (output)
    AttributeRemover_9_Output_1 -> AttributeRemover_9_Output (output)
AttributeRemover_7_Output (output)
AttributeRemover__Output (output)
AttributeRemover_9_Output (output)
AttributeRemover_11_Output (output)
AttributeRemover_14_Output (output)
AttributeRemover_15_Output (output)

FME custom transformer PollutantRelease

Parameters:
- XMPOLLUTANTRELEASE = @Value(xmPollutantRelease)   # xmPollutantRelease
- FACILITYREPORTID = @Value(FacilityReportID)   # FacilityReportID

Bookmark: PollutantRelease
PollutantRelease_Flat_Input (input)
    -> PollutantRelease_Flat
PollutantRelease_Flat: XMLFlattener
    EMBEDDED_EXPRESSIONS = PollutantRelease
    XML_SOURCE_TYPE = Attribute with XML document
    ATTRIBUTE_XML = xmPollutantRelease
    FLATTEN_OPTIONS = <structure separator="." map-empty-elements="yes" matched-prefix="attributes" matched-attributes="yes" cardinality="+{?}" structure-prefix="" child-position-attribute="" except-expression="" ui-mode="basic" matched-ancestor-attributes=""/>
    -> Frag_PollutantRelease
Frag_PollutantRelease: XMLFragmenter
    NEW_ATTRIBUTES = accidentalQuantity confidentialCode confidentialIndicator mediumCode methodBasisCode methodUsed pollutantCode remarkText totalQuantity
    EMBEDDED_EXPRESSIONS = PollutantRelease
    XML_SOURCE_TYPE = Attribute with XML document
    ATTRIBUTE_XML = xmPollutantRelease
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> True_confidentialIndicator
True_confidentialIndicator: NullAttributeMapper
    OTHER_VALUE = true
    NULL_TREATMENT = New Value
    ATTRLIST = confidentialIndicator
    NEW_VALUE = 1
    ATTRCHOICE = Selected Attributes
    -> False_confidentialIndicator
False_confidentialIndicator: NullAttributeMapper
    OTHER_VALUE = false
    NULL_TREATMENT = New Value
    ATTRLIST = confidentialIndicator
    NEW_VALUE = 0
    ATTRCHOICE = Selected Attributes
    -> Common_ConfidentialCodeType
Common_ConfidentialCodeType: FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_ConfidentialCodeType
    MSSQL_ADO_USE_SSPI = NO
    WHERE = value = '@Value(confidentialCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_ConfidentialCodeType,"value,id"
    dbo.Common_ConfidentialCodeType -> confidentialCodeRenamer
confidentialCodeRenamer: AttributeRenamer
    ATTR_LIST = id,confidentialCodeValue,@Value(id)
    -> Common_mediumCode
Common_mediumCode: FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_MediumCodeType
    MSSQL_ADO_USE_SSPI = NO
    WHERE = value = '@Value(mediumCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_MediumCodeType,"value,id"
    dbo.Common_MediumCodeType -> mediumCode_renamer
mediumCode_renamer: AttributeRenamer
    ATTR_LIST = id,mediumCodeValue,@Value(id)
    -> Common_PollutantType
Common_PollutantType: FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_PollutantType
    MSSQL_ADO_USE_SSPI = NO
    WHERE = value = '@Value(pollutantCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_PollutantType,"value,id"
    dbo.Common_PollutantType -> Common_PollutantType_2
Common_PollutantType_2: AttributeRenamer
    ATTR_LIST = id,pollutantCodeValue,@Value(id)
    -> Common_methodBasisCode_2
Common_methodBasisCode_2: FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_MethodBasisCodeType
    MSSQL_ADO_USE_SSPI = NO
    WHERE = value = '@Value(methodBasisCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_MethodBasisCodeType,"value,id"
    dbo.Common_MethodBasisCodeType -> methodBasisCode_renamer_2
methodBasisCode_renamer_2: AttributeRenamer
    ATTR_LIST = id,methodBasisCodeValue,@Value(id)
    -> AttributeCreator_6
AttributeCreator_6
    ATTR_LIST = xmlmethodUsed,@Value(xml_fragment)
    -> XMLFlattener_methodUsed_3
PollutantRelease: SQLExecutor
    MSSQL_ADO_ENCRYPT_CONNECTION = NO
    SQL_STATEMENT:
      FME_SQL_DELIMITER ;
      DECLARE @quantityID int
      DECLARE @methodID int

      BEGIN TRANSACTION
      begin try
      INSERT INTO [dbo].[MethodUsedType]
                 ([MethodTypeCode]
                 ,[Designation])
           VALUES
                 (@Value(idMethodTypeCode)
                 ,'@Value(DesignationMethod)')

      SET @methodID = (SELECT SCOPE_IDENTITY())

      INSERT INTO [dbo].[PollutantRelease]
                 ([mediumCode]
                 ,[pollutantCode]
                 ,[methodBasisCode]
                 ,[methodUsed]
                 ,[totalQuantity]
                 ,[accidentalQuantity]
                 ,[confidentialIndicator]
                 ,[confidentialCode]
                 ,[remarkText]
                 ,[facilityReportID])
           VALUES
                 (@Value(mediumCodeValue)
                 ,@Value(pollutantCodeValue)
                 ,@Value(methodBasisCodeValue)
                 ,@methodID
                 ,@Value(totalQuantity)
                 ,@Value(accidentalQuantity)
                 ,@Value(confidentialIndicator)
                 ,@Value(confidentialCodeValue)
                 ,'@Value(remarkText)'
                 ,@Value(FacilityReportID))

       SELECT SCOPE_IDENTITY() AS pollutantReleaseID, '' as ErrorMessag


       commit TRANSACTION


      end try
      begin catch
          ROLLBACK TRANSACTION
          SELECT 0 AS pollutantTransferID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = pollutantTransferID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> SQLExecutor_5_Initiator_1 (output)
SQLExecutor_5_Initiator_1 (output)

Bookmark: methodUsed
XMLFlattener_methodUsed_3
    EMBEDDED_EXPRESSIONS = methodUsed
    XML_SOURCE_TYPE = Attribute with XML document
    ATTRIBUTE_XML = xmlmethodUsed
    FLATTEN_OPTIONS = <structure separator="." map-empty-elements="yes" matched-prefix="attributes" matched-attributes="yes" cardinality="+{?}" structure-prefix="" child-position-attribute="" except-expression="" ui-mode="basic" matched-ancestor-attributes=""/>
    -> methodUsed_3
methodUsed_3: XMLFragmenter
    NEW_ATTRIBUTES = MethodTypeCode Designation
    EMBEDDED_EXPRESSIONS = methodUsed
    XML_SOURCE_TYPE = Attribute with XML document
    ATTRIBUTE_XML = xmlmethodUsed
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_4
FeatureReader_4
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_MethodTypeCodeType
    MSSQL_ADO_USE_SSPI = NO
    WHERE = value = '@Value(MethodTypeCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_MethodTypeCodeType,"value,id"
    dbo.Common_MethodTypeCodeType -> AttributeRenamer_7
AttributeRenamer_7
    ATTR_LIST = Designation,DesignationMethod,@Value(Designation),id,idMethodTypeCode,@Value(id)
    -> PollutantRelease

FME custom transformer FacilityReport

Parameters:
- _FILE_CONTENTS = @Value(_file_contents)   # File Contents
- XMLFACILITYREPORTS = @Value(xmlFacilityReports)   # xmlFacilityReports
- FACILITYREPORTSID = @Value(FacilityReportsID)   # FacilityReportsID

XMLFlattener_FacilityReports_Input (input)
    -> XMLFlattener_FacilityReports

Bookmark: FacilityReports
XMLFlattener_FacilityReports
    EMBEDDED_EXPRESSIONS = FacilityReports
    XML_SOURCE_TYPE = Attribute with XML document
    ATTRIBUTE_XML = _file_contents
    FLATTEN_OPTIONS = <structure separator="." map-empty-elements="yes" matched-prefix="attributes" matched-attributes="yes" cardinality="+{?}" structure-prefix="" child-position-attribute="" except-expression="" ui-mode="basic" matched-ancestor-attributes=""/>
    -> XMLFragmenter
XMLFragmenter
    NEW_ATTRIBUTES = dBFacitilyID operationHours protectVoluntaryData publicInformation totalEmployeeQuantity confidentialIndicator confidentialCode remarkText
    EMBEDDED_EXPRESSIONS = FacilityReport
    XML_SOURCE_TYPE = Attribute with XML document
    ATTRIBUTE_XML = xmlFacilityReports
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> AttributeCreator_2
AttributeCreator_2
    ATTR_LIST = xmlWasteTransfer,@Value(xml_fragment),xmlProductionVolume,@Value(xml_fragment),xmPollutantRelease,@Value(xml_fragment),xmlPollutantTransfer,@Value(xml_fragment)
    -> AttributeRemover_2
AttributeRemover_2
    REMOVE_ATTRS = _file_contents,id,xml_fragment,xml_id,xml_matched_element,xml_parent_child_pos,xml_parent_id
    -> NullAttributeMapper_5
NullAttributeMapper_5
    OTHER_VALUE = true
    NULL_TREATMENT = New Value
    ATTRLIST = protectVoluntaryData confidentialIndicator
    NEW_VALUE = 1
    ATTRCHOICE = Selected Attributes
    -> NullAttributeMapper_6
NullAttributeMapper_6
    OTHER_VALUE = false
    NULL_TREATMENT = New Value
    ATTRLIST = confidentialIndicator protectVoluntaryData
    NEW_VALUE = 0
    ATTRCHOICE = Selected Attributes
    -> FeatureReader_confidentialCode
FeatureReader_confidentialCode
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_ConfidentialCodeType
    MSSQL_ADO_USE_SSPI = NO
    WHERE = value = '@Value(confidentialCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_ConfidentialCodeType,"value,id"
    dbo.Common_ConfidentialCodeType -> AttributeRenamer_confidentialCode
AttributeRenamer_confidentialCode
    ATTR_LIST = id,idconfidentialCode,@Value(id)
    -> SQLExecutor_FacilityReport
SQLExecutor_FacilityReport
    MSSQL_ADO_ENCRYPT_CONNECTION = NO
    SQL_STATEMENT:
      FME_SQL_DELIMITER ;

      BEGIN TRANSACTION
      begin try
      INSERT INTO [dbo].[FacilityReport]
                 ([dBFacitilyID]
                 ,[operationHours]
                 ,[protectVoluntaryData]
                 ,[publicInformation]
                 ,[totalEmployeeQuantity]
                 ,[confidentialIndicator]
                 ,[confidentialCode]
                 ,[remarkText]
                 ,[facilityReportsID])
           VALUES
                 ('@Value(dBFacitilyID)'
                 ,@Value(operationHours)
                 ,@Value(protectVoluntaryData)
                 ,'@Value(publicInformation)'
                 ,@Value(totalEmployeeQuantity)
                 ,@Value(confidentialIndicator)
                 ,@Value(idconfidentialCode)
                 ,'@Value(remarkText)'
                 ,@Value(FacilityReportsID))
      SELECT SCOPE_IDENTITY() AS FacilityReportID, '' as ErrorMessag
      commit TRANSACTION

      end try
      begin catch
          ROLLBACK TRANSACTION
          SELECT 0 AS FacilityReportID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = FacilityReportID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> Tester_4
Tester_4
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> AttributeRemover_13
    PASSED -> Tester_4_Passed (output)
Tester_4_Passed (output)
AttributeRemover_13
    REMOVE_ATTRS = remarkText,xmlFacilityReports,confidentialCode,confidentialIndicator,dBFacitilyID,idconfidentialCode,operationHours,plantReportsID,protectVoluntaryData,publicInformation,reportID,totalEmployeeQuantity,value,xmlPlantReports
    -> WasteTransfer_2
    -> ProductionVolume_2
    -> PollutantTransfer
    -> PollutantRelease
WasteTransfer_2
    FACILITYREPORTID = @Value(FacilityReportID)
    XMLWASTETRANSFER = @Value(xmlWasteTransfer)
    SQLExecutor_3_Initiator_1 -> SQLExecutor_3_Initiator (output)
    SQLExecutor_3_Initiator_2 -> SQLExecutor_3_Initiator_2 (output)
SQLExecutor_3_Initiator_2 (output)
SQLExecutor_3_Initiator (output)
ProductionVolume_2
    FACILITYREPORTID = @Value(FacilityReportID)
    XMLPRODUCTIONVOLUME = @Value(xmlProductionVolume)
    SQLExecutor_2_Result_1 -> SQLExecutor_2_Result (output)
SQLExecutor_2_Result (output)
PollutantTransfer
    FACILITYREPORTID = @Value(FacilityReportID)
    XMLPOLLUTANTTRANSFER = @Value(xmlPollutantTransfer)
    SQLExecutor_4_Result_1 -> SQLExecutor_4_Result (output)
SQLExecutor_4_Result (output)
PollutantRelease
    FACILITYREPORTID = @Value(FacilityReportID)
    XMPOLLUTANTRELEASE = @Value(xmPollutantRelease)
    SQLExecutor_5_Initiator_1 -> SQLExecutor_5_Initiator (output)
SQLExecutor_5_Initiator (output)

FME custom transformer PlantReport

Parameters:
- REMARKTEXT = @Value(remarkText)   # remarkText
- DATEOFSTARTOPERATION = @Value(dateOfStartOperation)   # dateOfStartOperation
- XML_FRAGMENT = @Value(xml_fragment)   # Xml Fragment
- REFINERIES = @Value(refineries)   # refineries
- OPERATIONHOURS = @Value(operationHours)   # operationHours
- STATUSOFTHEPLANT = @Value(statusOfThePlant)   # statusOfThePlant
- SUBSTANTIALCHANGE = @Value(substantialChange)   # substantialChange
- DBPLANTID = @Value(dBPlantId)   # dBPlantId
- EXTENSIONBY50MWORMORE = @Value(extensionBy50MWOrMore)   # extensionBy50MWOrMore
- PLANTREPORTSID = @Value(plantReportsID)   # plantReportsID

AttributeCreator_2_Input (input)
    -> AttributeCreator_2

Bookmark: PlantReport
AttributeCreator_2
    ATTR_LIST = xmlcapacityAddedMW,@Value(xml_fragment),xmlcapacityAffectedMW,@Value(xml_fragment),xmlWith,@Value(xml_fragment),xmlPlantType,@Value(xml_fragment),xmlTotalEmisionToAir,@Value(xml_fragment),xmlEnergy,@Value(xml_fragment),xmlLCPDerogations,@Value(xml_fragment),xmlIEDArt72,@Value(xml_fragment)
    -> AttributeRemover_2
AttributeRemover_2
    REMOVE_ATTRS = _file_contents,id,xml_fragment,xml_id,xml_matched_element,xml_parent_child_pos,xml_parent_id
    -> XMLFlattener_mWth
NullAttributeMapper
    OTHER_VALUE = true
    NULL_TREATMENT = New Value
    ATTRLIST = extensionBy50MWOrMore refineries substantialChange
    NEW_VALUE = 1
    ATTRCHOICE = Selected Attributes
    -> NullAttributeMapper_2
NullAttributeMapper_2
    OTHER_VALUE = false
    NULL_TREATMENT = New Value
    ATTRLIST = extensionBy50MWOrMore refineries substantialChange
    NEW_VALUE = 0
    ATTRCHOICE = Selected Attributes
    -> PlantReport
PlantReport: SQLExecutor
    MSSQL_ADO_ENCRYPT_CONNECTION = NO
    SQL_STATEMENT:
      FME_SQL_DELIMITER ;
      DECLARE @mwithID int
      DECLARE @capaID int
      DECLARE @capaID2 int
      BEGIN TRANSACTION
      begin try
      INSERT INTO [dbo].[QuantityType]
                 ([Quantity]
                 ,[UnitCode])
           VALUES
                 (@Value(QuantityMwith)
                 ,@Value(idUnitCodeMwith))
      SET @mwithID = (SELECT SCOPE_IDENTITY())

      INSERT INTO [dbo].[QuantityType]
                 ([Quantity]
                 ,[UnitCode])
           VALUES
                 (@Value(QuantityCapa)
                 ,@Value(idUnitCodeCapa))
      SET @capaID = (SELECT SCOPE_IDENTITY())

      INSERT INTO [dbo].[QuantityType]
                 ([Quantity]
                 ,[UnitCode])
           VALUES
                 (@Value(QuantityCapa2)
                 ,@Value(idUnitCodeCapa2))
      SET @capaID2 = (SELECT SCOPE_IDENTITY())

      INSERT INTO [dbo].[PlantReport]
                 ([dBPlantId]
                 ,[statusOfThePlant]
                 ,[mWth]
                 ,[extensionBy50MWOrMore]
                 ,[capacityAddedMW]
                 ,[substantialChange]
                 ,[capacityAffectedMW]
                 ,[dateOfStartOperation]
                 ,[refineries]
                 ,[operationHours]
                 ,[remarkText]
                 ,[plantReportsID])
           VALUES
                 ('@Value(dBPlantId)'
                 ,@Value(statusOfThePlantValue)
                 ,@mwithID
                 ,@Value(extensionBy50MWOrMore)
                 ,@capaID
                 ,@Value(substantialChange)
                 ,@capaID2
                 ,'@Value(dateOfStartOperation)'
                 ,@Value(refineries)
                 ,@Value(operationHours)
                 ,'@Value(remarkText)'
                 ,@Value(plantReportsID))
       SELECT SCOPE_IDENTITY() AS plantReportID, '' as ErrorMessag


       commit TRANSACTION


      end try
      begin catch
          ROLLBACK TRANSACTION
          SELECT 0 AS plantReportID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = plantReportID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> Tester_3
Tester_3
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> AttributeRemover_6
AttributeRemover_6
    REMOVE_ATTRS = dateOfStartOperation,dBPlantId,ErrorMessag,extensionBy50MWOrMore,idUnitCodeCapa,idUnitCodeCapa2,idUnitCodeMwith,operationHours,Quantity ,QuantityCapa,QuantityCapa2,QuantityMwith,refineries,remarkText,statusOfThePlant,statusOfThePlantValue,UnitCode,xml_id,xml_matched_element,xml_parent_child_pos,xml_parent_id,xmlcapacityAddedMW,xmlcapacityAffectedMW,xmlPlantReports
    -> TotalEmissionsToAir_2
    -> EnergyInput_2
    -> PlantType_2
    -> LCPDerogations_2
    -> IEDArt72_2
TotalEmissionsToAir_2
    PLANTREPORTID = @Value(plantReportID)
    XMLTOTALEMISIONTOAIR = @Value(xmlTotalEmisionToAir)
    AttributeRemover_7_Output_2 -> AttributeRemover_7_Output_1 (output)
AttributeRemover_7_Output_1 (output)
EnergyInput_2
    XMLENERGY = @Value(xmlEnergy)
    PLANTREPORTID = @Value(plantReportID)
    AttributeRemover__Output_2 -> AttributeRemover__Output_1 (output)
AttributeRemover__Output_1 (output)
PlantType_2
    PLANTREPORTID = @Value(plantReportID)
    XMLPLANTTYPE = @Value(xmlPlantType)
    AttributeRemover_9_Output_2 -> AttributeRemover_9_Output_1 (output)
AttributeRemover_9_Output_1 (output)
LCPDerogations_2
    PLANTREPORTID = @Value(plantReportID)
    XMLLCPDEROGATIONS = @Value(xmlLCPDerogations)
    SUBSTANTIALCHANGE = @Value(substantialChange)
    AttributeRemover_11_Output_2 -> AttributeRemover_11_Output_1 (output)
AttributeRemover_11_Output_1 (output)
IEDArt72_2
    PLANTREPORTID = @Value(plantReportID)
    XMLLCPDEROGATIONS = @Value(xmlLCPDerogations)
    XMLIEDART72 = @Value(xmlIEDArt72)
    SUBSTANTIALCHANGE = @Value(substantialChange)
    AttributeRemover_14_Output_2 -> AttributeRemover_14_Output_1 (output)
    AttributeRemover_15_Output_2 -> AttributeRemover_15_Output_1 (output)
AttributeRemover_14_Output_1 (output)
AttributeRemover_15_Output_1 (output)

Bookmark: mWith
XMLFlattener_mWth
    EMBEDDED_EXPRESSIONS = mWth
    XML_SOURCE_TYPE = Attribute with XML document
    ATTRIBUTE_XML = xmlWith
    FLATTEN_OPTIONS = <structure separator="." map-empty-elements="yes" matched-prefix="attributes" matched-attributes="yes" cardinality="+{?}" structure-prefix="" child-position-attribute="" except-expression="" ui-mode="basic" matched-ancestor-attributes=""/>
    -> XML_Fragmenter_mWth
XML_Fragmenter_mWth: XMLFragmenter
    NEW_ATTRIBUTES = Quantity UnitCode
    EMBEDDED_EXPRESSIONS = mWth
    XML_SOURCE_TYPE = Attribute with XML document
    ATTRIBUTE_XML = xmlWith
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_UnitCode
FeatureReader_UnitCode
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_UnitCodeType
    MSSQL_ADO_USE_SSPI = NO
    WHERE = value = '@Value(UnitCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_UnitCodeType,"value,id"
    dbo.Common_UnitCodeType -> AttributeRenamerQuantity
AttributeRenamerQuantity
    ATTR_LIST = Quantity,QuantityMwith,@Value(Quantity),id,idUnitCodeMwith,@Value(id)
    -> AttributeRemover_XML_fragmenter
AttributeRemover_XML_fragmenter
    REMOVE_ATTRS = xml_fragment
    -> XMLFlattener_capacityAddedMW

Bookmark: capacityAddedMW
XMLFlattener_capacityAddedMW
    EMBEDDED_EXPRESSIONS = capacityAddedMW
    XML_SOURCE_TYPE = Attribute with XML document
    ATTRIBUTE_XML = xmlcapacityAddedMW
    FLATTEN_OPTIONS = <structure separator="." map-empty-elements="yes" matched-prefix="attributes" matched-attributes="yes" cardinality="+{?}" structure-prefix="" child-position-attribute="" except-expression="" ui-mode="basic" matched-ancestor-attributes=""/>
    -> capacityAddedMW
capacityAddedMW: XMLFragmenter
    NEW_ATTRIBUTES = Quantity  UnitCode
    EMBEDDED_EXPRESSIONS = capacityAddedMW
    XML_SOURCE_TYPE = Attribute with XML document
    ATTRIBUTE_XML = xmlcapacityAddedMW
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_3
FeatureReader_3
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_UnitCodeType
    MSSQL_ADO_USE_SSPI = NO
    WHERE = value = '@Value(UnitCode)'
    MSSQL_ADO_USER_NAME = sa
    MSSQL_ADO_QUERY_FEATURE_TYPES_FOR_MERGE_FILTERS = Yes
    COMBINE_GEOM = Use Result
    MSSQL_ADO_COMMAND_TIMEOUT = 30
    MSSQL_ADO_ENCRYPT_CONNECTION = NO
    ATTRIBUTES = dbo.Common_UnitCodeType,"value,id"
    dbo.Common_UnitCodeType -> AttributeRenamer_2
AttributeRenamer_2
    ATTR_LIST = Quantity,QuantityCapa,@Value(Quantity ),id,idUnitCodeCapa,@Value(id)
    -> AttributeRemover_4
AttributeRemover_4
    REMOVE_ATTRS = xml_fragment,xml_id,xml_matched_element,xml_parent_child_pos,xml_parent_id,xmlWith
    -> XMLFlattener_capacityAffectedMW

Bookmark: capacityAffectedMW
XMLFlattener_capacityAffectedMW
    EMBEDDED_EXPRESSIONS = capacityAffectedMW
    XML_SOURCE_TYPE = Attribute with XML document
    ATTRIBUTE_XML = xmlcapacityAffectedMW
    FLATTEN_OPTIONS = <structure separator="." map-empty-elements="yes" matched-prefix="attributes" matched-attributes="yes" cardinality="+{?}" structure-prefix="" child-position-attribute="" except-expression="" ui-mode="basic" matched-ancestor-attributes=""/>
    -> capacityAddedMW_capacityAffectedMW
capacityAddedMW_capacityAffectedMW: XMLFragmenter
    NEW_ATTRIBUTES = Quantity UnitCode
    EMBEDDED_EXPRESSIONS = capacityAffectedMW
    XML_SOURCE_TYPE = Attribute with XML document
    ATTRIBUTE_XML = xmlcapacityAffectedMW
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_4
FeatureReader_4
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_UnitCodeType
    MSSQL_ADO_USE_SSPI = NO
    WHERE = value = '@Value(UnitCode)'
    MSSQL_ADO_USER_NAME = sa
    MSSQL_ADO_QUERY_FEATURE_TYPES_FOR_MERGE_FILTERS = Yes
    COMBINE_GEOM = Use Result
    MSSQL_ADO_COMMAND_TIMEOUT = 30
    MSSQL_ADO_ENCRYPT_CONNECTION = NO
    ATTRIBUTES = dbo.Common_UnitCodeType,"value,id"
    dbo.Common_UnitCodeType -> AttributeRenamer_4
AttributeRenamer_4
    ATTR_LIST = Quantity,QuantityCapa2,@Value(Quantity ),id,idUnitCodeCapa2,@Value(id)
    -> AttributeRemover_5
AttributeRemover_5
    REMOVE_ATTRS = xml_fragment
    -> FeatureReader_StatusOfThePlantType
FeatureReader_StatusOfThePlantType
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_StatusOfThePlantType
    MSSQL_ADO_USE_SSPI = NO
    WHERE = value = '@Value(statusOfThePlant)'
    MSSQL_ADO_USER_NAME = sa
    MSSQL_ADO_QUERY_FEATURE_TYPES_FOR_MERGE_FILTERS = Yes
    COMBINE_GEOM = Use Result
    MSSQL_ADO_COMMAND_TIMEOUT = 30
    MSSQL_ADO_ENCRYPT_CONNECTION = NO
    ATTRIBUTES = dbo.Common_StatusOfThePlantType,"value,id"
    dbo.Common_StatusOfThePlantType -> AttributeRenamer_3
AttributeRenamer_3
    ATTR_LIST = id,statusOfThePlantValue,@Value(id)
    -> NullAttributeMapper

FME custom transformer TotalEmissionsToAir

Parameters:
- XMLTOTALEMISIONTOAIR = @Value(xmlTotalEmisionToAir)   # xmlTotalEmisionToAir
- PLANTREPORTID = @Value(plantReportID)   # plantReportID

XMLFlattener_TotalEmissionsToAir_Input (input)
    -> XMLFlattener_TotalEmissionsToAir

Bookmark: TotalEmissionToAir
XMLFlattener_TotalEmissionsToAir
    EMBEDDED_EXPRESSIONS = TotalEmissionsToAir
    XML_SOURCE_TYPE = Attribute with XML document
    ATTRIBUTE_XML = xmlTotalEmisionToAir
    FLATTEN_OPTIONS = <structure separator="." map-empty-elements="yes" matched-prefix="attributes" matched-attributes="yes" cardinality="+{?}" structure-prefix="" child-position-attribute="" except-expression="" ui-mode="basic" matched-ancestor-attributes=""/>
    -> XMLFrag_TotalEmissionsToAir
XMLFrag_TotalEmissionsToAir: XMLFragmenter
    NEW_ATTRIBUTES = type quantity
    EMBEDDED_EXPRESSIONS = TotalEmissionsToAir
    XML_SOURCE_TYPE = Attribute with XML document
    ATTRIBUTE_XML = xmlTotalEmisionToAir
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_5
FeatureReader_5
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_TotalEmissionsToAirType
    MSSQL_ADO_USE_SSPI = NO
    WHERE = value = '@Value(type)'
    MSSQL_ADO_USER_NAME = sa
    MSSQL_ADO_QUERY_FEATURE_TYPES_FOR_MERGE_FILTERS = Yes
    COMBINE_GEOM = Use Result
    MSSQL_ADO_COMMAND_TIMEOUT = 30
    MSSQL_ADO_ENCRYPT_CONNECTION = NO
    ATTRIBUTES = dbo.Common_TotalEmissionsToAirType,"value,id"
    dbo.Common_TotalEmissionsToAirType -> Rename_ID_value
Rename_ID_value: AttributeRenamer
    ATTR_LIST = id,TotalEmissionsToAirValue,@Value(id)
    -> totalEmissionsToAir
totalEmissionsToAir: SQLExecutor
    MSSQL_ADO_ENCRYPT_CONNECTION = NO
    SQL_STATEMENT:
      FME_SQL_DELIMITER ;
      begin try
      INSERT INTO [dbo].[TotalEmissionsToAir]
                 ([type]
                 ,[quantity]
                 ,[plantReportID])
           VALUES
                 (@Value(TotalEmissionsToAirValue)
                 ,@Value(quantity)
                 ,@Value(plantReportID))
       SELECT SCOPE_IDENTITY() AS totalEmissionsToAirID, '' as ErrorMessag

      end try
      begin catch
          SELECT  ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = totalEmissionsToAirID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> ErrorTester
ErrorTester: Tester
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> AttributeRemover_7
AttributeRemover_7
    -> AttributeRemover_7_Output_2 (output)
AttributeRemover_7_Output_2 (output)

FME custom transformer EnergyInput

Parameters:
- PLANTREPORTID = @Value(plantReportID)   # plantReportID
- XMLENERGY = @Value(xmlEnergy)   # xmlEnergy

Bookmark: EnergyInput
XMLFlattener_Energy_Input (input)
    -> XMLFlat_EnergyInput
XMLFlat_EnergyInput: XMLFlattener
    EMBEDDED_EXPRESSIONS = EnergyInput
    XML_SOURCE_TYPE = Attribute with XML document
    ATTRIBUTE_XML = xmlEnergy
    FLATTEN_OPTIONS = <structure separator="." map-empty-elements="yes" matched-prefix="attributes" matched-attributes="yes" cardinality="+{?}" structure-prefix="" child-position-attribute="" except-expression="" ui-mode="basic" matched-ancestor-attributes=""/>
    -> XMLFragEnergyInput
XMLFragEnergyInput: XMLFragmenter
    NEW_ATTRIBUTES = type quantity otherGases otherSolidFuels
    EMBEDDED_EXPRESSIONS = EnergyInput
    XML_SOURCE_TYPE = Attribute with XML document
    ATTRIBUTE_XML = xmlEnergy
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> typeFilterByValue
typeFilterByValue: FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_EnergyInputType
    MSSQL_ADO_USE_SSPI = NO
    WHERE = value = '@Value(type)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_EnergyInputType,"value,id"
    dbo.Common_EnergyInputType -> Rename_ID_Value
Rename_ID_Value: AttributeRenamer
    ATTR_LIST = id,EnergyInputTypeValue,@Value(id)
    -> otherGasesFilterByValue
otherGasesFilterByValue: FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_OtherGasesType
    MSSQL_ADO_USE_SSPI = NO
    WHERE = value = '@Value(otherGases)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_OtherGasesType,"value,id"
    dbo.Common_OtherGasesType -> Rename_ID_Value_2
Rename_ID_Value_2: AttributeRenamer
    ATTR_LIST = id,otherGasesValue,@Value(id)
    -> otherSolidFuelsFilterByValue
otherSolidFuelsFilterByValue: FeatureReader
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_OtherSolidFuels
    MSSQL_ADO_USE_SSPI = NO
    WHERE = value = '@Value(otherSolidFuels)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_OtherSolidFuels,"value,id"
    dbo.Common_OtherSolidFuels -> Rename_ID_Value_3
Rename_ID_Value_3: AttributeRenamer
    ATTR_LIST = id,otherSolidFuelsValue,@Value(id)
    -> EnergyInput
EnergyInput: SQLExecutor
    MSSQL_ADO_ENCRYPT_CONNECTION = NO
    SQL_STATEMENT:
      FME_SQL_DELIMITER ;
      begin try
      INSERT INTO [dbo].[EnergyInput]
                 ([type]
                 ,[otherGases]
                 ,[otherSolidFuels]
                 ,[quantity]
                 ,[plantReportID])
           VALUES
                 (@Value(EnergyInputTypeValue)
                 ,@Value(otherGasesValue)
                 ,@Value(otherSolidFuelsValue)
                 ,@Value(quantity)
                 ,@Value(plantReportID))
      SELECT SCOPE_IDENTITY() AS energyInputID, '' as ErrorMessag

      end try
      begin catch
          SELECT  ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = energyInputID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> ErrorTest
ErrorTest: Tester
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> AttributeRemover_
AttributeRemover_
    REMOVE_ATTRS = energyInputID,EnergyInputTypeValue,ErrorMessag,otherGases,otherGasesValue,otherSolidFuels,otherSolidFuelsValue,quantity,type,xml_fragment,xml_id,xml_matched_element,xml_parent_child_pos,xml_parent_id,xmlEnergy
    -> AttributeRemover__Output_2 (output)
AttributeRemover__Output_2 (output)

FME custom transformer WasteHandlerParty

Parameters:
- WASTETRANSFERID = @Value(WasteTransferID)   # WasteTransferID
- XMLWASTEHANDLERPARTY = @Value(xmlWasteHandlerParty)   # xmlWasteHandlerParty

Bookmark: New Bookmark
AttributeRemover_6_Input (input)
    -> AttributeRemover_6
AttributeRemover_6
    REMOVE_ATTRS = ErrorMessag,remarkText,xml_id,xml_matched_element,xml_parent_child_pos,xml_parent_id
    -> XMLFlattener_WaterHandlerParty
XMLFlattener_WaterHandlerParty
    EMBEDDED_EXPRESSIONS = WasteHandlerParty
    XML_SOURCE_TYPE = Attribute with XML document
    ATTRIBUTE_XML = xmlWasteHandlerParty
    FLATTEN_OPTIONS = <structure separator="." map-empty-elements="yes" matched-prefix="attributes" matched-attributes="yes" cardinality="+{?}" structure-prefix="" child-position-attribute="" except-expression="" ui-mode="basic" matched-ancestor-attributes=""/>
    -> XMLFrag_WasteHandlerParty
XMLFrag_WasteHandlerParty: XMLFragmenter
    NEW_ATTRIBUTES = address name siteAddress
    EMBEDDED_EXPRESSIONS = WasteHandlerParty
    XML_SOURCE_TYPE = Attribute with XML document
    ATTRIBUTE_XML = xmlWasteHandlerParty
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> AttributeCreator
AttributeCreator
    ATTR_LIST = xmladdress,@Value(xml_fragment),xmlsiteAddress,@Value(xml_fragment)
    -> NullAttributeMapper_7
NullAttributeMapper_7
    NULL_TREATMENT = New Value
    ATTRLIST = address name siteAddress
    NEW_VALUE = Null
    SOURCE_ATTR_VAL = Empty "Missing (Selected Attributes Only)" Null
    ATTRCHOICE = Selected Attributes
    -> Tester_6
Tester_6
    TEST_DESCRIPTION = ""
    TEST_MODE = Automatic
    TEST_CLAUSE:
      TEST @Value(address) = Null
      TEST @Value(siteAddress) = Null
      TEST @Value(name) = Null
    BOOL_OP = AND
    FAILED -> XMLFlattener_address
XMLFlattener_address
    EMBEDDED_EXPRESSIONS = address
    XML_SOURCE_TYPE = Attribute with XML document
    ATTRIBUTE_XML = xmladdress
    FLATTEN_OPTIONS = <structure separator="." map-empty-elements="yes" matched-prefix="attributes" matched-attributes="yes" cardinality="+{?}" structure-prefix="" child-position-attribute="" except-expression="" ui-mode="basic" matched-ancestor-attributes=""/>
    -> xml_WasteHandlerParty
xml_WasteHandlerParty: XMLFragmenter
    NEW_ATTRIBUTES = BuildingNumber City CountryID PostalCode StreetName
    EMBEDDED_EXPRESSIONS = address
    XML_SOURCE_TYPE = Attribute with XML document
    ATTRIBUTE_XML = xmladdress
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> NullAttributeMapper
NullAttributeMapper
    NULL_TREATMENT = New Value
    ATTRLIST = BuildingNumber City CountryID PostalCode StreetName
    NEW_VALUE = Null
    SOURCE_ATTR_VAL = Empty "Missing (Selected Attributes Only)" Null
    ATTRCHOICE = Selected Attributes
    -> Tester_Address
Tester_Address
    TEST_DESCRIPTION = ""
    TEST_MODE = Automatic
    TEST_CLAUSE:
      TEST @Value(City) = Null
      TEST @Value(BuildingNumber) = Null
      TEST @Value(CountryID) = Null
      TEST @Value(PostalCode) = Null
      TEST @Value(StreetName) = Null
    BOOL_OP = AND
    FAILED -> FeatureReader_12
FeatureReader_12
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_CountryCodeType
    MSSQL_ADO_USE_SSPI = NO
    WHERE = value = '@Value(CountryID)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_CountryCodeType,"value,id"
    dbo.Common_CountryCodeType -> AttributeRenamer_12
AttributeRenamer_12
    ATTR_LIST = id,idaddressCountry,@Value(CountryID),BuildingNumber,BuildingNumberAddress,@Value(BuildingNumber),City,CityAddress,@Value(City),PostalCode,PostalCodeAddress,@Value(PostalCode),StreetName,StreetNameAddress,@Value(StreetName)
    -> XMLFlattener_siteAddress
XMLFlattener_siteAddress
    EMBEDDED_EXPRESSIONS = siteAddress
    XML_SOURCE_TYPE = Attribute with XML document
    ATTRIBUTE_XML = xmlsiteAddress
    FLATTEN_OPTIONS = <structure separator="." map-empty-elements="yes" matched-prefix="attributes" matched-attributes="yes" cardinality="+{?}" structure-prefix="" child-position-attribute="" except-expression="" ui-mode="basic" matched-ancestor-attributes=""/>
    -> XMLFrag_siteAddress
XMLFrag_siteAddress: XMLFragmenter
    NEW_ATTRIBUTES = BuildingNumber City CountryID PostalCode StreetName
    EMBEDDED_EXPRESSIONS = siteAddress
    XML_SOURCE_TYPE = Attribute with XML document
    ATTRIBUTE_XML = xmlsiteAddress
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> NullAttributeMapper_4
NullAttributeMapper_4
    NULL_TREATMENT = New Value
    ATTRLIST = BuildingNumber City CountryID PostalCode StreetName
    NEW_VALUE = Null
    SOURCE_ATTR_VAL = Empty "Missing (Selected Attributes Only)" Null
    ATTRCHOICE = Selected Attributes
    -> Tester_8
Tester_8
    TEST_DESCRIPTION = ""
    TEST_MODE = Automatic
    TEST_CLAUSE:
      TEST @Value(City) = Null
      TEST @Value(BuildingNumber) = Null
      TEST @Value(CountryID) = Null
      TEST @Value(PostalCode) = Null
      TEST @Value(StreetName) = Null
    BOOL_OP = AND
    FAILED -> FeatureReader_3
FeatureReader_3
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_CountryCodeType
    MSSQL_ADO_USE_SSPI = NO
    WHERE = value = '@Value(CountryID)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_CountryCodeType,"value,id"
    dbo.Common_CountryCodeType -> AttributeRenamer_2
AttributeRenamer_2
    ATTR_LIST = id,idsiteAddressCountry,@Value(CountryID),BuildingNumber,BuildingNumberSiteAddress,@Value(BuildingNumber),City,CitySiteAddress,@Value(City),PostalCode,PostalCodeSiteAddress,@Value(PostalCode),StreetName,StreetNameSiteAddress,@Value(StreetName)
    -> WasteHandlerParty
WasteHandlerParty: SQLExecutor
    MSSQL_ADO_ENCRYPT_CONNECTION = NO
    SQL_STATEMENT:
      FME_SQL_DELIMITER ;
      DECLARE @Method int
      DECLARE @Method2 int

      BEGIN TRANSACTION
      begin try

      INSERT INTO [EPRTRlcp].[dbo].[AddressType]
                 ([StreetName]
                 ,[BuildingNumber]
                 ,[City]
                 ,[PostalCode]
                 ,[CountryID])
      VALUES
                 ('@Value(StreetNameAddress)'
                 ,'@Value(BuildingNumberAddress)'
                 ,'@Value(CityAddress)'
                 ,'@Value(PostalCodeAddress)'
                 ,'@Value(idaddressCountry)')

      SET @Method = (SELECT SCOPE_IDENTITY())

      INSERT INTO [EPRTRlcp].[dbo].[AddressType]
                 ([StreetName]
                 ,[BuildingNumber]
                 ,[City]
                 ,[PostalCode]
                 ,[CountryID])
      VALUES
                 ('@Value(StreetNameSiteAddress)'
                 ,'@Value(BuildingNumberSiteAddress)'
                 ,'@Value(CitySiteAddress)'
                 ,'@Value(PostalCodeSiteAddress)'
                 ,'@Value(idsiteAddressCountry)')

      SET @Method2 = (SELECT SCOPE_IDENTITY())

      INSERT INTO [dbo].[WasteHandlerParty]
                 ([name]
                 ,[address]
                 ,[siteAddress]
                 ,[wasteTransferID])
           VALUES
                 ('@Value(name)'
                 ,@Method
                 ,@Method2
                 ,@Value(WasteTransferID))
       SELECT SCOPE_IDENTITY() AS WasteHandlerPartyID, '' as ErrorMessag


       commit TRANSACTION


      end try
      begin catch
          ROLLBACK TRANSACTION
          SELECT 0 AS WasteHandlerPartyID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = WasteHandlerPartyID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> SQLExecutor_3_Initiator_3 (output)
SQLExecutor_3_Initiator_3 (output)

FME custom transformer WasteTransfer

Parameters:
- FACILITYREPORTID = @Value(FacilityReportID)   # FacilityReportID
- XMLWASTETRANSFER = @Value(xmlWasteTransfer)   # xmlWasteTransfer

XMLFlattener_WasteTransfer_Input (input)
    -> XMLFlattener_WasteTransfer

Bookmark: WasteTransfer
XMLFlattener_WasteTransfer
    EMBEDDED_EXPRESSIONS = WasteTransfer
    XML_SOURCE_TYPE = Attribute with XML document
    ATTRIBUTE_XML = xmlWasteTransfer
    FLATTEN_OPTIONS = <structure separator="." map-empty-elements="yes" matched-prefix="attributes" matched-attributes="yes" cardinality="+{?}" structure-prefix="" child-position-attribute="" except-expression="" ui-mode="basic" matched-ancestor-attributes=""/>
    -> XMLFrag_WasteTransfer
XMLFrag_WasteTransfer: XMLFragmenter
    NEW_ATTRIBUTES = wasteTypeCode wasteTreatmentCode quantity methodBasisCode confidentialIndicator confidentialCode remarkText
    EMBEDDED_EXPRESSIONS = WasteTransfer
    XML_SOURCE_TYPE = Attribute with XML document
    ATTRIBUTE_XML = xmlWasteTransfer
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> AttributeCreator_4
AttributeCreator_4
    ATTR_LIST = xmlmethodUsed,@Value(xml_fragment),xmlWasteHandlerParty,@Value(xml_fragment)
    -> NullAttributeMapper_2
NullAttributeMapper_2
    OTHER_VALUE = true
    NULL_TREATMENT = New Value
    ATTRLIST = confidentialIndicator
    NEW_VALUE = 1
    ATTRCHOICE = Selected Attributes
    -> NullAttributeMapper_3
NullAttributeMapper_3
    OTHER_VALUE = false
    NULL_TREATMENT = New Value
    ATTRLIST = confidentialIndicator
    NEW_VALUE = 0
    ATTRCHOICE = Selected Attributes
    -> FeatureReader_wasteTypeCode
FeatureReader_wasteTypeCode
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_WasteTypeCodeType
    MSSQL_ADO_USE_SSPI = NO
    WHERE = value = '@Value(wasteTypeCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_WasteTypeCodeType,"value,id"
    dbo.Common_WasteTypeCodeType -> AttributeRenamer_confidentialCode_2
AttributeRenamer_confidentialCode_2
    ATTR_LIST = id,idwasteTypeCode,@Value(id)
    -> FeatureReader_wasteTypeCode_2
FeatureReader_wasteTypeCode_2
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_WasteTreatmentCodeType
    MSSQL_ADO_USE_SSPI = NO
    WHERE = value = '@Value(wasteTreatmentCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_WasteTreatmentCodeType,"value,id"
    dbo.Common_WasteTreatmentCodeType -> AttributeRenamer_confidentialCode_3
AttributeRenamer_confidentialCode_3
    ATTR_LIST = id,idwasteTreatmentCode,@Value(id)
    -> FeatureReader_wasteTypeCode_3
FeatureReader_wasteTypeCode_3
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_MethodBasisCodeType
    MSSQL_ADO_USE_SSPI = NO
    WHERE = value = '@Value(methodBasisCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_MethodBasisCodeType,"value,id"
    dbo.Common_MethodBasisCodeType -> AttributeRenamer_methodBasisCode
AttributeRenamer_methodBasisCode
    ATTR_LIST = id,idmethodBasisCode,@Value(id)
    -> FeatureReader_confidentialCode_2
FeatureReader_confidentialCode_2
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_ConfidentialCodeType
    MSSQL_ADO_USE_SSPI = NO
    WHERE = value = '@Value(confidentialCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_ConfidentialCodeType,"value,id"
    dbo.Common_ConfidentialCodeType -> AttributeRenamer_WasteconfidentialCode
AttributeRenamer_WasteconfidentialCode
    ATTR_LIST = id,idWasteconfidentialCode,@Value(id)
    -> XMLFlattener_methodUsed
WasteTransfer: SQLExecutor
    MSSQL_ADO_ENCRYPT_CONNECTION = NO
    SQL_STATEMENT:
      FME_SQL_DELIMITER ;
      DECLARE @Method int

      BEGIN TRANSACTION
      begin try

      INSERT INTO [dbo].[MethodUsedType]
                 ([MethodTypeCode]
                 ,[Designation])
      VALUES
                 (@Value(idMethodTypeCode)
                 ,'@Value(DesignationMethod)')

      SET @Method = (SELECT SCOPE_IDENTITY())

      INSERT INTO [dbo].[WasteTransfer]
                 ([wasteTypeCode]
                 ,[wasteTreatmentCode]
                 ,[quantity]
                 ,[methodBasisCode]
                 ,[methodUsed]
                 ,[confidentialIndicator]
                 ,[confidentialCode]
                 ,[remarkText]
                 ,[facilityReportID])
           VALUES
                 (@Value(idwasteTypeCode)
                 ,@Value(idwasteTreatmentCode)
                 ,@Value(quantity)
                 ,@Value(idmethodBasisCode)
                 ,@Method
                 ,@Value(confidentialIndicator)
                 ,@Value(idWasteconfidentialCode)
                 ,'@Value(remarkText)'
                 ,@Value(FacilityReportID))
       SELECT SCOPE_IDENTITY() AS WasteTransferID, '' as ErrorMessag


       commit TRANSACTION


      end try
      begin catch
          ROLLBACK TRANSACTION
          SELECT 0 AS WasteTransferID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = WasteTransferID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> Tester_5
Tester_5
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    PASSED -> SQLExecutor_3_Initiator_2 (output)
    FAILED -> WasteHandlerParty_3
SQLExecutor_3_Initiator_2 (output)
WasteHandlerParty_3
    XMLWASTEHANDLERPARTY = @Value(xmlWasteHandlerParty)
    WASTETRANSFERID = @Value(WasteTransferID)
    SQLExecutor_3_Initiator_3 -> SQLExecutor_3_Initiator_1 (output)
SQLExecutor_3_Initiator_1 (output)

Bookmark: methodUsed
XMLFlattener_methodUsed
    EMBEDDED_EXPRESSIONS = methodUsed
    XML_SOURCE_TYPE = Attribute with XML document
    ATTRIBUTE_XML = xmlmethodUsed
    FLATTEN_OPTIONS = <structure separator="." map-empty-elements="yes" matched-prefix="attributes" matched-attributes="yes" cardinality="+{?}" structure-prefix="" child-position-attribute="" except-expression="" ui-mode="basic" matched-ancestor-attributes=""/>
    -> methodUsed
methodUsed: XMLFragmenter
    NEW_ATTRIBUTES = MethodTypeCode Designation
    EMBEDDED_EXPRESSIONS = methodUsed
    XML_SOURCE_TYPE = Attribute with XML document
    ATTRIBUTE_XML = xmlmethodUsed
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_2
FeatureReader_2
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_MethodTypeCodeType
    MSSQL_ADO_USE_SSPI = NO
    WHERE = value = '@Value(MethodTypeCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_MethodTypeCodeType,"value,id"
    dbo.Common_MethodTypeCodeType -> AttributeRenamer
AttributeRenamer
    ATTR_LIST = Designation,DesignationMethod,@Value(Designation),id,idMethodTypeCode,@Value(id)
    -> WasteTransfer

FME custom transformer PollutantTransfer

Parameters:
- XMLPOLLUTANTTRANSFER = @Value(xmlPollutantTransfer)   # xmlPollutantTransfer
- FACILITYREPORTID = @Value(FacilityReportID)   # FacilityReportID

Bookmark: PollutantTransfer
XMLFlattener_PlantType_Input_1 (input)
    -> XMLFlattener_PlantType
XMLFlattener_PlantType
    EMBEDDED_EXPRESSIONS = PollutantTransfer
    XML_SOURCE_TYPE = Attribute with XML document
    ATTRIBUTE_XML = xmlPollutantTransfer
    FLATTEN_OPTIONS = <structure separator="." map-empty-elements="yes" matched-prefix="attributes" matched-attributes="yes" cardinality="+{?}" structure-prefix="" child-position-attribute="" except-expression="" ui-mode="basic" matched-ancestor-attributes=""/>
    -> XMLFrag_PollutantTransfer
XMLFrag_PollutantTransfer: XMLFragmenter
    NEW_ATTRIBUTES = confidentialCode confidentialIndicator methodBasisCode methodUsed pollutantCode quantity remarkText
    EMBEDDED_EXPRESSIONS = PollutantTransfer
    XML_SOURCE_TYPE = Attribute with XML document
    ATTRIBUTE_XML = xmlPollutantTransfer
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> NullAttributeMapper_8
NullAttributeMapper_8
    OTHER_VALUE = true
    NULL_TREATMENT = New Value
    ATTRLIST = confidentialIndicator
    NEW_VALUE = 1
    ATTRCHOICE = Selected Attributes
    -> NullAttributeMapper_9
NullAttributeMapper_9
    OTHER_VALUE = false
    NULL_TREATMENT = New Value
    ATTRLIST = confidentialIndicator
    NEW_VALUE = 0
    ATTRCHOICE = Selected Attributes
    -> FeatureReader_6
FeatureReader_6
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_ConfidentialCodeType
    MSSQL_ADO_USE_SSPI = NO
    WHERE = value = '@Value(confidentialCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_ConfidentialCodeType,"value,id"
    dbo.Common_ConfidentialCodeType -> AttributeRenamer_9
AttributeRenamer_9
    ATTR_LIST = id,confidentialCodeValue,@Value(id)
    -> FeatureReader_5
FeatureReader_5
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_MethodBasisCodeType
    MSSQL_ADO_USE_SSPI = NO
    WHERE = value = '@Value(methodBasisCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_MethodBasisCodeType,"value,id"
    dbo.Common_MethodBasisCodeType -> AttributeRenamer_4
AttributeRenamer_4
    ATTR_LIST = id,methodBasisCodeValue,@Value(id)
    -> FeatureReader_7
FeatureReader_7
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_PollutantType
    MSSQL_ADO_USE_SSPI = NO
    WHERE = value = '@Value(pollutantCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_PollutantType,"value,id"
    dbo.Common_PollutantType -> AttributeRenamer_5
AttributeRenamer_5
    ATTR_LIST = id,pollutantCodeValue,@Value(id)
    -> AttributeCreator_5
AttributeCreator_5
    ATTR_LIST = xmlquantity,@Value(xml_fragment),xmlmethodUsed,@Value(xml_fragment)
    -> XMLFlattener_methodUsed_2
PollutantTransfer: SQLExecutor
    MSSQL_ADO_ENCRYPT_CONNECTION = NO
    SQL_STATEMENT:
      FME_SQL_DELIMITER ;
      DECLARE @quantityID int
      DECLARE @methodID int

      BEGIN TRANSACTION
      begin try
      INSERT INTO [dbo].[QuantityType]
                 ([Quantity]
                 ,[UnitCode])
           VALUES
                 (@Value(Quantityquantity)
                 ,@Value(idUnitCodequantity))
      SET @quantityID = (SELECT SCOPE_IDENTITY())

      INSERT INTO [dbo].[MethodUsedType]
                 ([MethodTypeCode]
                 ,[Designation])
           VALUES
                 (@Value(idMethodTypeCode)
                 ,@Value(DesignationMethod))

      SET @methodID = (SELECT SCOPE_IDENTITY())

      INSERT INTO [dbo].[PollutantTransfer]
                 ([pollutantCode]
                 ,[methodBasisCode]
                 ,[methodUsed]
                 ,[quantity]
                 ,[confidentialIndicator]
                 ,[confidentialCode]
                 ,[remarkText]
                 ,[facilityReportID])
           VALUES
                 (@Value(pollutantCodeValue)
                 ,@Value(methodBasisCodeValue)
                 ,@methodID
                 ,@quantityID
                 ,@Value(confidentialIndicator)
                 ,@Value(confidentialCodeValue)
                 ,@Value(remarkText)
                 ,@Value(FacilityReportID))

       SELECT SCOPE_IDENTITY() AS pollutantTransferID, '' as ErrorMessag


       commit TRANSACTION


      end try
      begin catch
          ROLLBACK TRANSACTION
          SELECT 0 AS pollutantTransferID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = pollutantTransferID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> SQLExecutor_4_Result_1 (output)
SQLExecutor_4_Result_1 (output)

Bookmark: methodUsed
XMLFlattener_methodUsed_2
    EMBEDDED_EXPRESSIONS = methodUsed
    XML_SOURCE_TYPE = Attribute with XML document
    ATTRIBUTE_XML = xmlmethodUsed
    FLATTEN_OPTIONS = <structure separator="." map-empty-elements="yes" matched-prefix="attributes" matched-attributes="yes" cardinality="+{?}" structure-prefix="" child-position-attribute="" except-expression="" ui-mode="basic" matched-ancestor-attributes=""/>
    -> methodUsed_2
methodUsed_2: XMLFragmenter
    NEW_ATTRIBUTES = MethodTypeCode Designation
    EMBEDDED_EXPRESSIONS = methodUsed
    XML_SOURCE_TYPE = Attribute with XML document
    ATTRIBUTE_XML = xmlmethodUsed
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_8
FeatureReader_8
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_MethodTypeCodeType
    MSSQL_ADO_USE_SSPI = NO
    WHERE = value = '@Value(MethodTypeCode)'
    MSSQL_ADO_USER_NAME = sa
    MSSQL_ADO_QUERY_FEATURE_TYPES_FOR_MERGE_FILTERS = Yes
    COMBINE_GEOM = Use Result
    MSSQL_ADO_ENCRYPT_CONNECTION = NO
    MSSQL_ADO_COMMAND_TIMEOUT = 30
    ATTRIBUTES = dbo.Common_MethodTypeCodeType,"value,id"
    dbo.Common_MethodTypeCodeType -> AttributeRenamer_6
AttributeRenamer_6
    ATTR_LIST = Designation,DesignationMethod,@Value(Designation),id,idMethodTypeCode,@Value(id)
    -> XMLFlattener_quantity_2

Bookmark: Quantity
XMLFlattener_quantity_2
    EMBEDDED_EXPRESSIONS = quantity
    XML_SOURCE_TYPE = Attribute with XML document
    ATTRIBUTE_XML = xmlquantity
    FLATTEN_OPTIONS = <structure separator="." map-empty-elements="yes" matched-prefix="attributes" matched-attributes="yes" cardinality="+{?}" structure-prefix="" child-position-attribute="" except-expression="" ui-mode="basic" matched-ancestor-attributes=""/>
    -> quantity_2
quantity_2: XMLFragmenter
    NEW_ATTRIBUTES = Quantity UnitCode
    EMBEDDED_EXPRESSIONS = quantity
    XML_SOURCE_TYPE = Attribute with XML document
    ATTRIBUTE_XML = xmlquantity
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> FeatureReader_9
FeatureReader_9
    FEATURETYPES_RADIO = FEATURETYPES
    MSSQL_ADO_PASSWORD =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
    FORMAT = MSSQL_ADO
    MSSQL_ADO_SERVER = eeapc8235
    OUTPUT_FEATURES_DISPLAY = Based on Connections
    DATASET = EPRTRlcp
    ATTR_CONFLICT_RES = Use Result
    ATTR_ACCUM_MODE = Merge Initiator and Result
    FEATURETYPES = dbo.Common_UnitCodeType
    MSSQL_ADO_USE_SSPI = NO
    WHERE = value = '@Value(UnitCode)'
    MSSQL_ADO_USER_NAME = sa
    MSSQL_ADO_QUERY_FEATURE_TYPES_FOR_MERGE_FILTERS = Yes
    COMBINE_GEOM = Use Result
    MSSQL_ADO_COMMAND_TIMEOUT = 30
    MSSQL_ADO_ENCRYPT_CONNECTION = NO
    ATTRIBUTES = dbo.Common_UnitCodeType,"value,id"
    dbo.Common_UnitCodeType -> AttributeRenamer_3
AttributeRenamer_3
    ATTR_LIST = Quantity,Quantityquantity,@Value(Quantity),id,idUnitCodequantity,@Value(id)
    -> PollutantTransfer

FME custom transformer LCPDerogations

Parameters:
- PLANTREPORTID = @Value(plantReportID)   # plantReportID
- SUBSTANTIALCHANGE = @Value(substantialChange)   # substantialChange
- XMLLCPDEROGATIONS = @Value(xmlLCPDerogations)   # xmlLCPDerogations

XMLFlattener_PlantType_2_Input (input)
    -> XMLFlattener_PlantType_2

Bookmark: LCPDerogations
XMLFlattener_PlantType_2
    EMBEDDED_EXPRESSIONS = LCPDerogations
    XML_SOURCE_TYPE = Attribute with XML document
    ATTRIBUTE_XML = xmlLCPDerogations
    FLATTEN_OPTIONS = <structure separator="." map-empty-elements="yes" matched-prefix="attributes" matched-attributes="yes" cardinality="+{?}" structure-prefix="" child-position-attribute="" except-expression="" ui-mode="basic" matched-ancestor-attributes=""/>
    -> AttributeRemover_10
AttributeRemover_10
    REMOVE_ATTRS = xmlEnergy,xmlTotalEmisionToAir,xml_fragment
    -> XMLFrag_LCPDerogations
XMLFrag_LCPDerogations: XMLFragmenter
    NEW_ATTRIBUTES = art32TNP art33LLD art34SIS art35DHP usefulHeatProductionRollingAverage5Years
    EMBEDDED_EXPRESSIONS = LCPDerogations
    XML_SOURCE_TYPE = Attribute with XML document
    ATTRIBUTE_XML = xmlLCPDerogations
    MERGE_ATTRS = Yes
    FLATTEN_OPTIONS = <structure separator="." map-empty-elements="yes" matched-prefix="attributes" matched-attributes="yes" cardinality="+{?}" structure-prefix="" child-position-attribute="" except-expression="" ui-mode="basic" matched-ancestor-attributes=""/>
    FRAGMENTS -> NullAttributeMapper_True
NullAttributeMapper_True
    OTHER_VALUE = true
    NULL_TREATMENT = New Value
    ATTRLIST = art32TNP art33LLD art34SIS art35DHP substantialChange
    NEW_VALUE = 1
    ATTRCHOICE = Selected Attributes
    -> NullAttributeMapper_False
NullAttributeMapper_False
    OTHER_VALUE = false
    NULL_TREATMENT = New Value
    ATTRLIST = art32TNP art33LLD art34SIS art35DHP substantialChange
    NEW_VALUE = 0
    ATTRCHOICE = Selected Attributes
    -> LCPDerogations
LCPDerogations: SQLExecutor
    MSSQL_ADO_ENCRYPT_CONNECTION = NO
    SQL_STATEMENT:
      FME_SQL_DELIMITER ;
      BEGIN TRANSACTION
      begin try
      INSERT INTO [dbo].[LCPDerogations]
                 ([art32TNP]
                 ,[art33LLD]
                 ,[art34SIS]
                 ,[art35DHP]
                 ,[usefulHeatProductionRollingAverage5Years]
                 ,[plantReportID])
           VALUES
                 (@Value(art32TNP)
                 ,@Value(art33LLD)
                 ,@Value(art34SIS)
                 ,@Value(art35DHP)
                 ,@Value(usefulHeatProductionRollingAverage5Years)
                 ,@Value(plantReportID))

       SELECT SCOPE_IDENTITY() AS LCPDerogationsID, '' as ErrorMessag


       commit TRANSACTION


      end try
      begin catch
          ROLLBACK TRANSACTION
          SELECT 0 AS LCPDerogationsID, ERROR_MESSAGE() AS ErrorMessag
      end catch;
    MSSQL_ADO_USER_NAME = sa
    DATASET = EPRTRlcp
    COMBINE_ATTRS = Keep Result Attributes if Conflict
    MSSQL_ADO_COMMAND_TIMEOUT = 30
    EXPOSED_ATTRIBUTE_LIST = LCPDerogationsID,ErrorMessag
    MSSQL_ADO_SERVER = eeapc8235
    COMBINE_GEOM = Initiator Geometry Only
    MSSQL_ADO_QUERY_FEATURE_TYPES_FOR_MERGE_FILTERS = Yes
    MSSQL_ADO_USE_SSPI = NO
    FORMAT = MSSQL_ADO
    MSSQL_ADO_PASSWORD =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
    RESULT -> ErrorTester
ErrorTester: Tester
    TEST_DESCRIPTION = ""
    TEST_MODE = Automatic
    TEST_CLAUSE:
      TEST ErrorMessag NOT_ATTRIBUTE_VALUE_NULL ""
      TEST ErrorMessag NOT_ATTRIBUTE_IS_EMPTY ""
      TEST ErrorMessag NOT_ATTRIBUTE_IS_MISSING ""
    BOOL_OP = AND
    FAILED -> AttributeRemover_11
AttributeRemover_11
    REMOVE_ATTRS = art32TNP,art33LLD,art34SIS,art35DHP,LCPDerogationsID,substantialChange,usefulHeatProductionRollingAverage5Years,xml_fragment,xml_id,xml_matched_element,xml_parent_child_pos,xml_parent_id,xmlFacilityReports,xmlLCPDerogations
    -> AttributeRemover_11_Output_2 (output)
AttributeRemover_11_Output_2 (output)
