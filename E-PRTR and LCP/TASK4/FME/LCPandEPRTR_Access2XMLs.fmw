FME workspace LCPandEPRTR_Access2XMLs.fmw

Parameters:
- SourceDataset_MDB_ADO =   # Source Microsoft Access Database File(s)

Readers:
- MDB_ADO_1: MDB_ADO from $(SourceDataset_MDB_ADO)

Writers:
- DATAFILE_1: DATAFILE to LCPandEPRTR

Bookmark: Build plantsReports
DesulphurisationRate (reader MDB_ADO_1)
    attributes: month long, quantity double, desulphurisationRateID autonumber, iEDArt72ID long
    -> DesulphurisationRate [input 1]
SO2 (reader MDB_ADO_1)
    attributes: month long, quantity double, sO2ID autonumber, iEDArt72ID long
    -> SO2 [input 1]
IEDArt72 (reader MDB_ADO_1)
    attributes: iEDArt72_4a yesno, iEDArt72_4b yesno, remarkText memo, iEDArt72ID autonumber, plantReportID long
    -> IEDArt72 [input 1]
TotalEmissionsToAir (reader MDB_ADO_1)
    attributes: type long, quantity double, totalEmissionsToAirID autonumber, plantReportID long
    -> TotalEmissionsToAir [input 1]
EnergyInput (reader MDB_ADO_1)
    attributes: type long, otherGases long, otherSolidFuels long, quantity double, energyInputID autonumber, plantReportID long
    -> EnergyInput [input 1]
PlantType (reader MDB_ADO_1)
    attributes: combustionPlantType long, thermalInput long, plantTypeID autonumber, plantReportID long
    -> PlantType [input 1]
LCPDerogations (reader MDB_ADO_1)
    attributes: art32TNP yesno, art33LLD yesno, art34SIS yesno, art35DHP yesno, usefulHeatProductionRollingAverage5Years double, lCPDerogationsID autonumber, plantReportID long
    -> LCPDerogations
LCPDerogations: XMLTemplater
    RESULT_ATTRIBUTE = _LCPDerogations
    CONSECUTIVE_GROUPS = No
    VISIBLE_QUERY_VALIDATE = Yes
    ROOT_QUERY_EXPR:
      <LCPDerogations>
        <art32TNP>{fme:get-attribute("art32TNP")}</art32TNP>
        <art33LLD>{fme:get-attribute("art33LLD")}</art33LLD>
        <art34SIS>{fme:get-attribute("art34SIS")}</art34SIS>
        <art35DHP>{fme:get-attribute("art35DHP")}</art35DHP>
        <usefulHeatProductionRollingAverage5Years>{fme:get-attribute("usefulHeatProductionRollingAverage5Years")}</usefulHeatProductionRollingAverage5Years>
      </LCPDerogations>
    OUTPUT_XML_HEADER = No
    GROUP_BY = lCPDerogationsID
    -> AttributeRemover_6
AttributeRemover_6
    REMOVE_ATTRS = art32TNP,art33LLD,art34SIS,art35DHP,lCPDerogationsID,usefulHeatProductionRollingAverage5Years
    -> PlantReport [input 10]
PlantReport (reader MDB_ADO_1)
    attributes: dBPlantId text(255), statusOfThePlant long, mWth long, extensionBy50MWOrMore yesno, capacityAddedMW long, substantialChange yesno, capacityAffectedMW long, dateOfStartOperation datetime, refineries yesno, operationHours double, remarkText memo, plantReportID autonumber, plantReportsID long
    -> PlantReport [input 1]
DesulphurisationRate: XMLTemplater
    RESULT_ATTRIBUTE = _DesulphurisationRate
    VISIBLE_QUERY_VALIDATE = Yes
    ROOT_QUERY_EXPR:
      <DesulphurisationRate>
        {fme:process-features("MONTH","MonthId",{fme:get-attribute("month")})}
       <quantity>{fme:get-attribute("quantity")}</quantity>
      </DesulphurisationRate>
    OUTPUT_XML_HEADER = No
    MONTH_QUERY_EXPR:
       {
      for $valueRef in {fme:get-attribute("MonthId")}
      return(
      <month>{fme:get-attribute("MonthValue")}</month>
      )
      }
    -> AttributeRemover_2
AttributeRemover_2
    REMOVE_ATTRS = desulphurisationRateID,month,quantity
    -> IEDArt72 [input 2]
SO2: XMLTemplater
    RESULT_ATTRIBUTE = _SO2
    VISIBLE_QUERY_VALIDATE = Yes
    ROOT_QUERY_EXPR:
      <SO2>
       {fme:process-features("MONTH","MonthId",{fme:get-attribute("month")})}
       <quantity>{fme:get-attribute("quantity")}</quantity>
      </SO2>
    OUTPUT_XML_HEADER = No
    MONTH_QUERY_EXPR:
       {
      for $valueRef in {fme:get-attribute("MonthId")}
      return(
      <month>{fme:get-attribute("MonthValue")}</month>
      )
      }
    -> AttributeRemover
AttributeRemover
    REMOVE_ATTRS = month,quantity,sO2ID
    -> IEDArt72 [input 3]
IEDArt72: XMLTemplater
    DESULPHURISATIONRATE_QUERY_EXPR:
       {
      for $valueRef in {fme:get-attribute("iEDArt72ID")}
      return(
          {fme:get-xml-attribute("_DesulphurisationRate")}
      )
      }
    SO2_QUERY_EXPR:
       {
      for $valueRef in {fme:get-attribute("iEDArt72ID")}
      return(
          {fme:get-xml-attribute("_SO2")}
      )
      }
    RESULT_ATTRIBUTE = _IEDArt72
    VISIBLE_QUERY_VALIDATE = Yes
    ROOT_QUERY_EXPR:
      <IEDArt72>
        <iEDArt72_4a>{fme:get-attribute("iEDArt72_4a")}</iEDArt72_4a>
        <iEDArt72_4b>{fme:get-attribute("iEDArt72_4b")}</iEDArt72_4b>
        <remarkText>{fme:get-attribute("remarkText")}</remarkText>
         {fme:process-features("DESULPHURISATIONRATE","iEDArt72ID",{fme:get-attribute("iEDArt72ID")})}
         {fme:process-features("SO2","iEDArt72ID",{fme:get-attribute("iEDArt72ID")})}
      </IEDArt72>
    OUTPUT_XML_HEADER = No
    -> AttributeRemover_7
AttributeRemover_7
    REMOVE_ATTRS = iEDArt72_4a,iEDArt72_4b,iEDArt72ID,remarkText
    -> PlantReport [input 11]
TotalEmissionsToAir: XMLTemplater
    RESULT_ATTRIBUTE = _TotalEmissionsToAir
    VISIBLE_QUERY_VALIDATE = Yes
    TYPE_QUERY_EXPR:
       {
      for $valueRef in {fme:get-attribute("TotalEmissionsToAirID")}
      return(
          <type>{fme:get-attribute("TotalEmissionsToAirValue")}</type>
      )
      }
    ROOT_QUERY_EXPR:
      <TotalEmissionsToAir>
       {fme:process-features("TYPE","TotalEmissionsToAirID",{fme:get-attribute("type")})}
       <quantity>{fme:get-attribute("quantity")}</quantity>
      </TotalEmissionsToAir>
    OUTPUT_XML_HEADER = No
    -> AttributeRemover_3
AttributeRemover_3
    REMOVE_ATTRS = quantity,totalEmissionsToAirID,type
    -> PlantReport [input 7]
EnergyInput: XMLTemplater
    OTHERGASES_QUERY_EXPR:
       {
      for $valueRef in {fme:get-attribute("OhterGasesID")}
      return(
        <otherGases>{fme:get-attribute("OtherGasesValue")}</otherGases>
      )
      }
    RESULT_ATTRIBUTE = _EnergyInput
    OTHERSOLIDFUELS_QUERY_EXPR:
       {
      for $valueRef in {fme:get-attribute("OtherSolidFuelsID")}
      return(
          <otherSolidFuels>{fme:get-attribute("OtherSolidFuelsValue")}</otherSolidFuels>
      )
      }
    VISIBLE_QUERY_VALIDATE = Yes
    TYPE_QUERY_EXPR:
       {
      for $valueRef in {fme:get-attribute("EnergyInputID")}
      return(
          <type>{fme:get-attribute("EnergyInputValue")}</type>
      )
      }
    ROOT_QUERY_EXPR:
      <EnergyInput>
        {fme:process-features("OTHERGASES","OtherGasesID",{fme:get-attribute("otherGases")})}
        {fme:process-features("TYPE","EnergyInputID",{fme:get-attribute("type")})}
        {fme:process-features("OTHERSOLIDFUELS","OtherSolidFuelsID",{fme:get-attribute("otherSolidFuels")})}
        <quantity>{fme:get-attribute("quantity")}</quantity>
       </EnergyInput>
    OUTPUT_XML_HEADER = No
    -> AttributeRemover_4
AttributeRemover_4
    REMOVE_ATTRS = energyInputID,otherGases,otherSolidFuels,quantity,type
    -> PlantReport [input 8]
PlantType: XMLTemplater
    THERMALINPUT_QUERY_EXPR:
       {
      for $valueRef in {fme:get-attribute("quantityTypeID")}
      return(
       <thermalInput>
          <common:Quantity xmlns:common="http://dd.eionet.europa.eu/schemas/LCPandPRTR/LCPandPRTRCommon">{fme:get-attribute("Quantity")}</common:Quantity>
          {fme:process-features("UNITCODE","UnitCodeID",{fme:get-attribute("UnitCode")})}
       </thermalInput>
       )
       }
    COMBUSTIONPLANTTYPE_QUERY_EXPR:
       {
      for $valueRef in {fme:get-attribute("CombustionID")}
      return(
      <combustionPlantType>{fme:get-attribute("CombustionValue")}</combustionPlantType>
      )
      }
    RESULT_ATTRIBUTE = _PlantType
    UNITCODE_QUERY_EXPR:
       {
      for $valueRef in {fme:get-attribute("UnitCodeID")}
      return(
      <common:UnitCode xmlns:common="http://dd.eionet.europa.eu/schemas/LCPandPRTR/LCPandPRTRCommon">{fme:get-attribute("UnitCodeValue")}</common:UnitCode>
      )
      }
    VISIBLE_QUERY_VALIDATE = Yes
    ROOT_QUERY_EXPR:
      <PlantType>
        {fme:process-features("COMBUSTIONPLANTTYPE","CombustionID",{fme:get-attribute("combustionPlantType")})}
        {fme:process-features("THERMALINPUT","quantityTypeID",{fme:get-attribute("plantTypeID")})}
      </PlantType>
    OUTPUT_XML_HEADER = No
    -> AttributeRemover_5
AttributeRemover_5
    REMOVE_ATTRS = combustionPlantType,plantTypeID,thermalInput
    -> PlantReport [input 9]
PlantReport: XMLTemplater
    CAPACITYAFFECTEDMW_QUERY_EXPR:
       {
      for $valueRef in {fme:get-attribute("quantityTypeID")}
      return(
      <capacityAffectedMW>
        <common:Quantity xmlns:common="http://dd.eionet.europa.eu/schemas/LCPandPRTR/LCPandPRTRCommon">{fme:get-attribute("Quantity")}</common:Quantity>
         {fme:process-features("UNITCODE","UnitCodeID",{fme:get-attribute("UnitCode")})}
      </capacityAffectedMW>
      )
      }
    UNITCODE_QUERY_EXPR:
       {
      for $valueRef in {fme:get-attribute("UnitCodeID")}
      return(
      <common:UnitCode xmlns:common="http://dd.eionet.europa.eu/schemas/LCPandPRTR/LCPandPRTRCommon">{fme:get-attribute("UnitCodeValue")}</common:UnitCode>
      )
      }
    ENERGYINPUT_QUERY_EXPR:
       {
      for $valueRef in {fme:get-attribute("plantReportID")}
      return(
          {fme:get-xml-attribute("_EnergyInput")}
      )
      }
    CAPACITYADDEDMW_QUERY_EXPR:
       {
      for $valueRef in {fme:get-attribute("quantityTypeID")}
      return(
      <capacityAddedMW>
        <common:Quantity xmlns:common="http://dd.eionet.europa.eu/schemas/LCPandPRTR/LCPandPRTRCommon">{fme:get-attribute("Quantity")}</common:Quantity>
         {fme:process-features("UNITCODE","UnitCodeID",{fme:get-attribute("UnitCode")})}
      </capacityAddedMW>
      )
      }
    TOTALEMISSIONSTOAIR_QUERY_EXPR:
       {
      for $valueRef in {fme:get-attribute("plantReportID")}
      return(
          {fme:get-xml-attribute("_TotalEmissionsToAir")}
      )
      }
    MWTH_QUERY_EXPR:
       {
      for $valueRef in {fme:get-attribute("quantityTypeID")}
      return(
      <mWth>
       <common:Quantity xmlns:common="http://dd.eionet.europa.eu/schemas/LCPandPRTR/LCPandPRTRCommon">{fme:get-attribute("Quantity")}</common:Quantity>
        {fme:process-features("UNITCODE","UnitCodeID",{fme:get-attribute("UnitCode")})}
      </mWth>
      )
      }
    RESULT_ATTRIBUTE = _PlantReport
    OUTPUT_XML_HEADER = No
    LCPDEROGATIONS_QUERY_EXPR:
       {
      for $valueRef in {fme:get-attribute("plantReportID")}
      return(
          {fme:get-xml-attribute("_LCPDerogations")}
      )
      }
    STATUSOFTHEPLANT_QUERY_EXPR:
      {
      for $valueRef in {fme:get-attribute("StatusOfThePlantID")}
      return(
          <statusOfThePlant>{fme:get-attribute("StatusOfThePlantValue")}</statusOfThePlant>
      )
      }
    ROOT_QUERY_EXPR:
      <PlantReport xmlns:common="http://dd.eionet.europa.eu/schemas/LCPandPRTR/LCPandPRTRCommon">
        <dBPlantId>{fme:get-attribute("dBPlantId")}</dBPlantId>
        {fme:process-features("STATUSOFTHEPLANT","StatusOfThePlantID",{fme:get-attribute("statusOfThePlant")})}
        {fme:process-features("MWTH","quantityTypeID",{fme:get-attribute("mWth")})}
        <extensionBy50MWOrMore>{fme:get-attribute("extensionBy50MWOrMore")}</extensionBy50MWOrMore>
        {fme:process-features("CAPACITYADDEDMW","quantityTypeID",{fme:get-attribute("capacityAddedMW")})}
        <substantialChange>{fme:get-attribute("substantialChange")}</substantialChange>
        {fme:process-features("CAPACITYAFFECTEDMW","quantityTypeID",{fme:get-attribute("capacityAffectedMW")})}
        <dateOfStartOperation>{fme:get-attribute("dateOfStartOperation")}</dateOfStartOperation>
        <refineries>{fme:get-attribute("refineries")}</refineries>
        <operationHours>{fme:get-attribute("operationHours")}</operationHours>
        <remarkText>{fme:get-attribute("remarkText")}</remarkText>
        {fme:process-features("TOTALEMISSIONSTOAIR","plantReportID",{fme:get-attribute("plantReportID")})}
        {fme:process-features("ENERGYINPUT","plantReportID",{fme:get-attribute("plantReportID")})}
        {fme:process-features("PLANTTYPE","plantReportID",{fme:get-attribute("plantReportID")})}
        {fme:process-features("LCPDEROGATIONS","plantReportID",{fme:get-attribute("plantReportID")})}
        {fme:process-features("IEDART72","plantReportID",{fme:get-attribute("plantReportID")})}
      </PlantReport>
    PLANTTYPE_QUERY_EXPR:
       {
      for $valueRef in {fme:get-attribute("plantReportID")}
      return(
          {fme:get-xml-attribute("_PlantType")}
      )
      }
    VISIBLE_QUERY_VALIDATE = Yes
    IEDART72_QUERY_EXPR:
       {
      for $valueRef in {fme:get-attribute("plantReportID")}
      return(
          {fme:get-xml-attribute("_IEDArt72")}
      )
      }
    -> AttributeRemover_8

Bookmark: Build FacilityReports
FacilityReport (reader MDB_ADO_1)
    attributes: dBFacitilyID text(255), operationHours long, protectVoluntaryData yesno, publicInformation memo, totalEmployeeQuantity long, confidentialIndicator yesno, confidentialCode long, remarkText memo, facilityReportID autonumber, facilityReportsID long
    -> FacilityReport [input 1]
PollutantTransfer (reader MDB_ADO_1)
    attributes: pollutantCode long, methodBasisCode long, methodUsed long, quantity double, confidentialIndicator yesno, confidentialCode long, remarkText memo, pollutantTransferID autonumber, facilityReportID long
    -> PollutantTransfer [input 1]
WasteTransfer (reader MDB_ADO_1)
    attributes: wasteTypeCode long, wasteTreatmentCode long, quantity double, methodBasisCode long, methodUsed long, confidentialIndicator yesno, confidentialCode long, remarkText memo, wasteTransferID autonumber, facilityReportID long
    -> WasteTransfer [input 1]
WasteHandlerParty (reader MDB_ADO_1)
    attributes: name text(255), address long, siteAddress long, wasteHandlerPartyID autonumber, wasteTransferID long
    -> WasteHandlerParty [input 1]
ProductionVolume (reader MDB_ADO_1)
    attributes: productName text(255), quantity long, productionVolumeID autonumber, facilityReportID long
    -> ProductionVolume [input 1]
PollutantRelease (reader MDB_ADO_1)
    attributes: mediumCode long, pollutantCode long, methodBasisCode long, methodUsed long, totalQuantity double, accidentalQuantity double, confidentialIndicator yesno, confidentialCode long, remarkText memo, pollutantReleaseID autonumber, facilityReportID long
    -> PollutantRelease [input 1]
WasteHandlerParty: XMLTemplater
    RESULT_ATTRIBUTE = _WasteHandlerParty
    VISIBLE_QUERY_VALIDATE = Yes
    SITEADDRESS_QUERY_EXPR:
       {
      for $valueRef in {fme:get-attribute("addressTypeID")}
      return(
         <siteAddress>
          <common:StreetName xmlns:common="http://dd.eionet.europa.eu/schemas/LCPandPRTR/LCPandPRTRCommon">{fme:get-attribute("StreetName")}</common:StreetName>
          <common:BuildingNumber xmlns:common="http://dd.eionet.europa.eu/schemas/LCPandPRTR/LCPandPRTRCommon">{fme:get-attribute("BuildingNumber")}</common:BuildingNumber>
          <common:City xmlns:common="http://dd.eionet.europa.eu/schemas/LCPandPRTR/LCPandPRTRCommon">{fme:get-attribute("City")}</common:City>
          <common:PostalCode xmlns:common="http://dd.eionet.europa.eu/schemas/LCPandPRTR/LCPandPRTRCommon">{fme:get-attribute("PostalCode")}</common:PostalCode>
          <common:CountryID xmlns:common="http://dd.eionet.europa.eu/schemas/LCPandPRTR/LCPandPRTRCommon">{fme:get-attribute("CountryID")}</common:CountryID>
        </siteAddress>
        )
        }
    ADDRESS_QUERY_EXPR:
       {
      for $valueRef in {fme:get-attribute("addressTypeID")}
      return(
          <address>
           <common:StreetName xmlns:common="http://dd.eionet.europa.eu/schemas/LCPandPRTR/LCPandPRTRCommon">{fme:get-attribute("StreetName")}</common:StreetName>
           <common:BuildingNumber xmlns:common="http://dd.eionet.europa.eu/schemas/LCPandPRTR/LCPandPRTRCommon">{fme:get-attribute("BuildingNumber")}</common:BuildingNumber>
           <common:City xmlns:common="http://dd.eionet.europa.eu/schemas/LCPandPRTR/LCPandPRTRCommon">{fme:get-attribute("City")}</common:City>
           <common:PostalCode xmlns:common="http://dd.eionet.europa.eu/schemas/LCPandPRTR/LCPandPRTRCommon">{fme:get-attribute("PostalCode")}</common:PostalCode>
           <common:CountryID xmlns:common="http://dd.eionet.europa.eu/schemas/LCPandPRTR/LCPandPRTRCommon">{fme:get-attribute("CountryID")}</common:CountryID>
         </address>
         )
         }
    ROOT_QUERY_EXPR:
      <WasteHandlerParty>
          <name>{fme:get-attribute("name")}</name>
         {fme:process-features("ADDRESS","addressTypeID",{fme:get-attribute("address")})}
         {fme:process-features("SITEADDRESS","addressTypeID",{fme:get-attribute("siteAddress")})}
      </WasteHandlerParty>
    OUTPUT_XML_HEADER = No
    -> WasteTransfer [input 7]
PollutantTransfer: XMLTemplater
    RESULT_ATTRIBUTE = _pollutantTransfer
    METHODBASISCODE_QUERY_EXPR:
       {
      for $valueRef in {fme:get-attribute("MethodBasisCodeID")}
      return(
          <methodBasisCode>{fme:get-attribute("MethodBasisCodeValue")}</methodBasisCode>
      )
      }
    VISIBLE_QUERY_VALIDATE = Yes
    ROOT_QUERY_EXPR:
      <PollutantTransfer>
              {fme:process-features("POLLUTANTCODE","PollutantCodeID",{fme:get-attribute("pollutantCode")})}
              {fme:process-features("METHODBASISCODE","MethodBasisCodeID",{fme:get-attribute("methodBasisCode")})}
              {fme:process-features("METHODUSED","MethodUsedID",{fme:get-attribute("methodUsed")})}
              <quantity>{fme:get-attribute("quantity")}</quantity>
              <confidentialIndicator>{fme:get-attribute("confidentialIndicator")}</confidentialIndicator>
              {fme:process-features("CONFIDENTIALCODE","ConfidentialCodeID",{fme:get-attribute("confidentialCode")})}
              <remarkText>{fme:get-attribute("remarkText")}</remarkText>
            </PollutantTransfer>
    OUTPUT_XML_HEADER = No
    CONFIDENTIALCODE_QUERY_EXPR:
      {
      for $valueRef in {fme:get-attribute("ConfidentialCodeID")}
      return(
      <confidentialCode>{fme:get-attribute("ConfidentialCodeValue")}</confidentialCode>
      )
      }
    METHODUSED_QUERY_EXPR:
       {
      for $valueRef in {fme:get-attribute("methodUsedTypeID")}
      return(
              <methodUsed>
                <common:MethodTypeCode xmlns:common="http://dd.eionet.europa.eu/schemas/LCPandPRTR/LCPandPRTRCommon">{fme:get-attribute("MethodTypeCode")}</common:MethodTypeCode>
                <common:Designation xmlns:common="http://dd.eionet.europa.eu/schemas/LCPandPRTR/LCPandPRTRCommon">{fme:get-attribute("Designation")}</common:Designation>
              </methodUsed>
      )
      }
    POLLUTANTCODE_QUERY_EXPR:
       {
      for $valueRef in {fme:get-attribute("PollutantID")}
      return(
      <pollutantCode>{fme:get-attribute("PollutantValue")}</pollutantCode>
      )
      }
    -> AttributeRemover_9
AttributeRemover_9
    REMOVE_ATTRS = confidentialCode,confidentialIndicator,methodBasisCode,methodUsed,pollutantCode,pollutantTransferID,quantity,remarkText
    -> FacilityReport [input 2]
WasteTransfer: XMLTemplater
    WASTETREATMENTCODE_QUERY_EXPR:
       {
      for $valueRef in {fme:get-attribute("WasteTreatmentCodeID")}
      return(
          <wasteTreatmentCode>{fme:get-attribute("WasteTreatmentCodeValue")}</wasteTreatmentCode>
      )
      }
    RESULT_ATTRIBUTE = _wasteTransfer
    METHODBASISCODE_QUERY_EXPR:
      {
      for $valueRef in {fme:get-attribute("MethodBasisCodeID")}
      return(
              <methodBasisCode>{fme:get-attribute("MethodBasisCodeValue")}</methodBasisCode>
      )
      }
    WASTEHANDLERPARTY_QUERY_EXPR:
       {
      for $valueRef in {fme:get-attribute("wasteTransferID")}
      return(
          {fme:get-xml-attribute("_WasteHandlerParty")}
      )
      }
    VISIBLE_QUERY_VALIDATE = Yes
    ROOT_QUERY_EXPR:
            <WasteTransfer>
              {fme:process-features("WASTETYPECODE","WasteTypeCodeID",{fme:get-attribute("wasteTypeCode")})}
              {fme:process-features("WASTETREATMENTCODE","WasteTreatmentCodeID",{fme:get-attribute("wasteTreatmentCode")})}
              <quantity>{fme:get-attribute("quantity")}</quantity>
              {fme:process-features("METHODBASISCODE","MethodBasisCodeID",{fme:get-attribute("methodBasisCode")})}
              {fme:process-features("METHODUSED","MethodUsedID",{fme:get-attribute("methodUsed")})}
              <confidentialIndicator>{fme:get-attribute("confidentialIndicator")}</confidentialIndicator>
              {fme:process-features("CONFIDENTIALCODE","ConfidentialCodeID",{fme:get-attribute("confidentialCode")})}
              <remarkText>{fme:get-attribute("remarkText")}</remarkText>
             {fme:process-features("WASTEHANDLERPARTY","wasteTransferID",{fme:get-attribute("wasteTransferID")})}
            </WasteTransfer>
    OUTPUT_XML_HEADER = No
    WASTETYPECODE_QUERY_EXPR:
       {
      for $valueRef in {fme:get-attribute("WasteTypeCodeID")}
      return(
          <wasteTypeCode>{fme:get-attribute("WasteTypeCodeValue")}</wasteTypeCode>
      )
      }
    CONFIDENTIALCODE_QUERY_EXPR:
       {
      for $valueRef in {fme:get-attribute("ConfidentialCodeID")}
      return(
          <confidentialCode>{fme:get-attribute("ConfidentialCodeValue")}</confidentialCode>
      )
      }
    METHODUSED_QUERY_EXPR:
       {
      for $valueRef in {fme:get-attribute("methodUsedTypeID")}
      return(
      <methodUsed>
        <common:MethodTypeCode xmlns:common="http://dd.eionet.europa.eu/schemas/LCPandPRTR/LCPandPRTRCommon">{fme:get-attribute("MethodTypeCode")}</common:MethodTypeCode>
        <common:Designation xmlns:common="http://dd.eionet.europa.eu/schemas/LCPandPRTR/LCPandPRTRCommon">{fme:get-attribute("Designation")}</common:Designation>
      </methodUsed>
      )
      }
    -> AttributeRemover_12
AttributeRemover_12
    REMOVE_ATTRS = confidentialCode,confidentialIndicator,methodBasisCode,methodUsed,quantity,remarkText,wasteTransferID,wasteTreatmentCode,wasteTypeCode
    -> FacilityReport [input 3]
PollutantRelease: XMLTemplater
    RESULT_ATTRIBUTE = _pollutantRelease
    MEDIUMCODE_QUERY_EXPR:
       {
      for $valueRef in {fme:get-attribute("MediumCodeID")}
      return(
      <mediumCode>{fme:get-attribute("MediumCodeValue")}</mediumCode>
      )
      }
    METHODBASISCODE_QUERY_EXPR:
      {
      for $valueRef in {fme:get-attribute("MethodBasisCodeID")}
      return(
          <methodBasisCode>{fme:get-attribute("methodBasisCode")}</methodBasisCode>
      )
      }
    VISIBLE_QUERY_VALIDATE = Yes
    ROOT_QUERY_EXPR:
      <PollutantRelease>
              {fme:process-features("MEDIUMCODE","MediumCodeID",{fme:get-attribute("mediumCode")})}
              {fme:process-features("POLLUTANTCODE","PollutantID",{fme:get-attribute("pollutantCode")})}
              {fme:process-features("METHODBASISCODE","MethodBasisCodeID",{fme:get-attribute("methodBasisCode")})}
              {fme:process-features("METHODUSED","methodUsedTypeID",{fme:get-attribute("methodUsed")})}
              <totalQuantity>{fme:get-attribute("totalQuantity")}</totalQuantity>
              <accidentalQuantity>{fme:get-attribute("accidentalQuantity")}</accidentalQuantity>
              <confidentialIndicator>{fme:get-attribute("confidentialIndicator")}</confidentialIndicator>
              {fme:process-features("CONFIDENTIALCODE","ConfidentialCodeID",{fme:get-attribute("confidentialCode")})}
              <remarkText>{fme:get-attribute("remarkText")}</remarkText>
            </PollutantRelease>
    OUTPUT_XML_HEADER = No
    CONFIDENTIALCODE_QUERY_EXPR:
       {
      for $valueRef in {fme:get-attribute("ConfidentialCodeID")}
      return(
      <confidentialCode>{fme:get-attribute("ConfidentialCodeValue")}</confidentialCode>
      )
      }
    METHODUSED_QUERY_EXPR:
       {
      for $valueRef in {fme:get-attribute("methodUsedTypeID")}
      return(
              <methodUsed>
                <common:MethodTypeCode xmlns:common="http://dd.eionet.europa.eu/schemas/LCPandPRTR/LCPandPRTRCommon">{fme:get-attribute("MethodTypeCode")}</common:MethodTypeCode>
                <common:Designation xmlns:common="http://dd.eionet.europa.eu/schemas/LCPandPRTR/LCPandPRTRCommon">{fme:get-attribute("Designation")}</common:Designation>
              </methodUsed>
      )
      }
    POLLUTANTCODE_QUERY_EXPR:
       {
      for $valueRef in {fme:get-attribute("PollutantID")}
      return(
      <pollutantCode>{fme:get-attribute("PollutantValue")}</pollutantCode>
      )
      }
    -> AttributeRemover_10
AttributeRemover_10
    REMOVE_ATTRS = accidentalQuantity,confidentialCode,confidentialIndicator,mediumCode,methodBasisCode,methodUsed,pollutantCode,pollutantReleaseID,remarkText,totalQuantity
    -> FacilityReport [input 5]
ProductionVolume: XMLTemplater
    RESULT_ATTRIBUTE = _productionVolume
    QUANTITY_QUERY_EXPR:
       {
      for $valueRef in {fme:get-attribute("quantityTypeID")}
      return(
              <quantity>
                <common:Quantity xmlns:common="http://dd.eionet.europa.eu/schemas/LCPandPRTR/LCPandPRTRCommon">{fme:get-attribute("Quantity")}</common:Quantity>
                 {fme:process-features("UNITCODE","UnitCodeID",{fme:get-attribute("UnitCode")})}
              </quantity>
      )
      }
    UNITCODE_QUERY_EXPR:
       {
      for $valueRef in {fme:get-attribute("UnitCodeID")}
      return(
      <common:UnitCode xmlns:common="http://dd.eionet.europa.eu/schemas/LCPandPRTR/LCPandPRTRCommon">{fme:get-attribute("UnitCodeValue")}</common:UnitCode>
      )
      }
    VISIBLE_QUERY_VALIDATE = Yes
    ROOT_QUERY_EXPR:
      <ProductionVolume>
              <productName>{fme:get-attribute("productName")}</productName>
              {fme:process-features("QUANTITY","quantityTypeID",{fme:get-attribute("quantity")})}
            </ProductionVolume>
    OUTPUT_XML_HEADER = No
    -> AttributeRemover_11
AttributeRemover_11
    REMOVE_ATTRS = productionVolumeID,productName,quantity
    -> FacilityReport [input 4]
FacilityReport: XMLTemplater
    RESULT_ATTRIBUTE = _FacilityReport
    POLLUTANTRELEASE_QUERY_EXPR:
       {
      for $valueRef in {fme:get-attribute("facilityReportID")}
      return(
          {fme:get-xml-attribute("_pollutantRelease")}
      )
      }
    VISIBLE_QUERY_VALIDATE = Yes
    POLLUTANTTRANSFER_QUERY_EXPR:
       {
      for $valueRef in {fme:get-attribute("facilityReportID")}
      return(
          {fme:get-xml-attribute("_pollutantTransfer")}
      )
      }
    WASTETRANSFER_QUERY_EXPR:
       {
      for $valueRef in {fme:get-attribute("facilityReportID")}
      return(
          {fme:get-xml-attribute("_wasteTransfer")}
      )
      }
    ROOT_QUERY_EXPR:
          <FacilityReport>
            <dBFacitilyID>{fme:get-attribute("dBFacitilyID")}</dBFacitilyID>
            <operationHours>{fme:get-attribute("operationHours")}</operationHours>
            <protectVoluntaryData>{fme:get-attribute("protectVoluntaryData")}</protectVoluntaryData>
            <publicInformation>{fme:get-attribute("publicInformation")}</publicInformation>
            <totalEmployeeQuantity>{fme:get-attribute("totalEmployeeQuantity")}</totalEmployeeQuantity>
            <confidentialIndicator>{fme:get-attribute("confidentialIndicator")}</confidentialIndicator>
            <confidentialCode></confidentialCode>
            <remarkText>{fme:get-attribute("remarkText")}</remarkText>
             {fme:process-features("POLLUTANTTRANSFER","facilityReportID",{fme:get-attribute("facilityReportID")})}
             {fme:process-features("WASTETRANSFER","facilityReportID",{fme:get-attribute("facilityReportID")})}
             {fme:process-features("PRODUCTIONVOLUME","facilityReportID",{fme:get-attribute("facilityReportID")})}
             {fme:process-features("POLLUTANTRELEASE","facilityReportID",{fme:get-attribute("facilityReportID")})}
          </FacilityReport>
    OUTPUT_XML_HEADER = No
    PRODUCTIONVOLUME_QUERY_EXPR:
       {
      for $valueRef in {fme:get-attribute("facilityReportID")}
      return(
          {fme:get-xml-attribute("_productionVolume")}
      )
      }
    -> AttributeRemover_13

Bookmark: Enumerations
Common_OtherGasesType (reader MDB_ADO_1)
    attributes: value text(255), id autonumber
    -> OtherGasesRenamer
OtherGasesRenamer: AttributeRenamer
    ATTR_LIST = id,OhterGasesID,@Value(id),value,OtherGasesValue,@Value(value)
    -> EnergyInput [input 2]
Common_StatusOfThePlantType (reader MDB_ADO_1)
    attributes: value text(255), id autonumber
    -> StatusOfThePlantRenamer
StatusOfThePlantRenamer: AttributeRenamer
    ATTR_LIST = id,StatusOfThePlantID,@Value(id),value,StatusOfThePlantValue,@Value(value)
    -> PlantReport [input 2]
Common_OtherSolidFuels (reader MDB_ADO_1)
    attributes: value text(255), id autonumber
    -> OtherSolidFuelsRenamer
OtherSolidFuelsRenamer: AttributeRenamer
    ATTR_LIST = id,OtherSolidFuelsID,@Value(id),value,OtherSolidFuelsValue,@Value(value)
    -> EnergyInput [input 4]
Common_MonthType (reader MDB_ADO_1)
    attributes: value text(255), id autonumber
    -> MonthTypeRenamer
MonthTypeRenamer: AttributeRenamer
    ATTR_LIST = id,MonthId,@Value(id),value,MonthValue,@Value(value)
    -> DesulphurisationRate [input 2]
    -> SO2 [input 2]
Common_TotalEmissionsToAirType (reader MDB_ADO_1)
    attributes: value text(255), id autonumber
    -> TotalEmissionsToAirRenamer
TotalEmissionsToAirRenamer: AttributeRenamer
    ATTR_LIST = id,TotalEmissionsToAirID,@Value(id),value,TotalEmissionsToAirValue,@Value(value)
    -> TotalEmissionsToAir [input 2]
Common_EnergyInputType (reader MDB_ADO_1)
    attributes: value text(255), id autonumber
    -> EnergyInputRenamer
EnergyInputRenamer: AttributeRenamer
    ATTR_LIST = id,EnergyInputID,@Value(id),value,EnergyInputValue,@Value(value)
    -> EnergyInput [input 3]
Common_CombustionType (reader MDB_ADO_1)
    attributes: value text(255), id autonumber
    -> CombustionRenamer
CombustionRenamer: AttributeRenamer
    ATTR_LIST = id,CombustionID,@Value(id),value,CombustionValue,@Value(value)
    -> PlantType [input 4]

Bookmark: Enumerations
Common_WasteTypeCodeType (reader MDB_ADO_1)
    attributes: value text(255), id autonumber
    -> WasteTypeCodeRenamer
WasteTypeCodeRenamer: AttributeRenamer
    ATTR_LIST = id,WasteTypeCodeID,@Value(id),value,WasteTypeCodeValue,@Value(value)
    -> WasteTransfer [input 2]
Common_WasteTreatmentCodeType (reader MDB_ADO_1)
    attributes: value text(255), id autonumber
    -> WasteTreatmentCodeType
WasteTreatmentCodeType: AttributeRenamer
    ATTR_LIST = id,WasteTreatmentCodeID,@Value(id),value,WasteTreatmentCodeValue,@Value(value)
    -> WasteTransfer [input 3]
Common_MethodTypeCodeType (reader MDB_ADO_1)
    attributes: value text(255), id autonumber
    -> MethodTypeCodeRenamer
MethodTypeCodeRenamer: AttributeRenamer
    ATTR_LIST = id,MethodTypeCodeID,@Value(id),value,MethodTypeCodeValue,@Value(value)
AddressType (reader MDB_ADO_1)
    attributes: StreetName text(255), BuildingNumber text(255), City text(255), PostalCode text(255), CountryID text(255), addressTypeID autonumber
    -> WasteHandlerParty [input 2]
    -> WasteHandlerParty [input 3]
MethodUsedType (reader MDB_ADO_1)
    attributes: MethodTypeCode long, Designation text(255), methodUsedTypeID autonumber
    -> PollutantRelease [input 5]
    -> WasteTransfer [input 5]
    -> PollutantTransfer [input 4]
Common_MediumCodeType (reader MDB_ADO_1)
    attributes: value text(255), id autonumber
    -> MediumCodeRenamer
MediumCodeRenamer: AttributeRenamer
    ATTR_LIST = id,MediumCodeID,@Value(id),value,MediumCodeValue,@Value(value)
    -> PollutantRelease [input 2]
Common_PollutantType (reader MDB_ADO_1)
    attributes: value text(255), id autonumber
    -> PollutantRenamer
PollutantRenamer: AttributeRenamer
    ATTR_LIST = id,PollutantID,@Value(id),value,PollutantValue,@Value(value)
    -> PollutantRelease [input 3]
    -> PollutantTransfer [input 2]
Common_MethodBasisCodeType (reader MDB_ADO_1)
    attributes: value text(255), id autonumber
    -> MethodBasisCodeRenamer
MethodBasisCodeRenamer: AttributeRenamer
    ATTR_LIST = id,MethodBasisCodeID,@Value(id),value,MethodBasisCodeValue,@Value(value)
    -> PollutantRelease [input 4]
    -> WasteTransfer [input 4]
    -> PollutantTransfer [input 3]
Common_ConfidentialCodeType (reader MDB_ADO_1)
    attributes: value text(255), id autonumber
    -> ConfidentialCodeRenamer
ConfidentialCodeRenamer: AttributeRenamer
    ATTR_LIST = id,ConfidentialCodeID,@Value(id),value,ConfidentialCodeValue,@Value(value)
    -> PollutantRelease [input 6]
    -> WasteTransfer [input 6]
    -> PollutantTransfer [input 5]

Bookmark: Build Reports
Common_UnitCodeType (reader MDB_ADO_1)
    attributes: value text(255), id autonumber
    -> UnitCodeRenamer
UnitCodeRenamer: AttributeRenamer
    ATTR_LIST = id,UnitCodeID,@Value(id),value,UnitCodeValue,@Value(value)
    -> PlantType [input 3]
    -> PlantReport [input 6]
    -> ProductionVolume [input 3]
QuantityType (reader MDB_ADO_1)
    attributes: Quantity double, UnitCode long, quantityTypeID autonumber
    -> PlantType [input 2]
    -> PlantReport [input 4]
    -> PlantReport [input 5]
    -> PlantReport [input 3]
    -> ProductionVolume [input 2]
AttributeRemover_8
    REMOVE_ATTRS = capacityAddedMW,capacityAffectedMW,dateOfStartOperation,dBPlantId,extensionBy50MWOrMore,mWth,operationHours,plantReportID,refineries,remarkText,statusOfThePlant,substantialChange
    -> PlantReports [input 2]
AttributeRemover_13
    REMOVE_ATTRS = confidentialCode,confidentialIndicator,dBFacitilyID,facilityReportID,operationHours,protectVoluntaryData,publicInformation,remarkText,totalEmployeeQuantity
    -> FacilityReports [input 2]
PlantReports (reader MDB_ADO_1)
    attributes: plantReportsID autonumber, reportID long
    -> PlantReports [input 1]
PlantReports: XMLTemplater
    RESULT_ATTRIBUTE = _PlantReports
    PLANTREPORT_QUERY_EXPR:
       {
      for $valueRef in {fme:get-attribute("plantReportsID")}
      return(
          {fme:get-xml-attribute("_PlantReport")}
      )
      }
    VISIBLE_QUERY_VALIDATE = Yes
    ROOT_QUERY_EXPR:
      <PlantReports>
       {fme:process-features("PLANTREPORT","plantReportsID",{fme:get-attribute("plantReportsID")})}
      </PlantReports>
    OUTPUT_XML_HEADER = No
    -> LCPandPRTR [input 3]
Report (reader MDB_ADO_1)
    attributes: countryID long, remarkText memo, reportingYear long, reportID autonumber
    -> Counter
Counter
    DOMAIN = counter
    CNT_ATTR = _count
    SCOPE = Global
    START = 0
    -> LCPandPRTR [input 1]
Common_CountryCodeType (reader MDB_ADO_1)
    attributes: value text(255), id autonumber
    -> CountryCodeRenamer
CountryCodeRenamer: AttributeRenamer
    ATTR_LIST = id,CountryCodeID,@Value(id),value,CountryCodeValue,@Value(value)
    -> LCPandPRTR [input 2]
FacilityReports (reader MDB_ADO_1)
    attributes: facilityReportsID autonumber, reportID long
    -> FacilityReports [input 1]
FacilityReports: XMLTemplater
    RESULT_ATTRIBUTE = _FacilityReports
    FACILITYREPORT_QUERY_EXPR:
       {
      for $valueRef in {fme:get-attribute("facilityReportsID")}
      return(
          {fme:get-xml-attribute("_FacilityReport")}
      )
      }
    VISIBLE_QUERY_VALIDATE = Yes
    ROOT_QUERY_EXPR:
       <FacilityReports>
          {fme:process-features("FACILITYREPORT","facilityReportsID",{fme:get-attribute("facilityReportsID")})}
       </FacilityReports>
    OUTPUT_XML_HEADER = No
    -> LCPandPRTR [input 4]
LCPandPRTR: XMLTemplater
    RESULT_ATTRIBUTE = _result
    COUNTRYID_QUERY_EXPR:
       {
      for $valueRef in {fme:get-attribute("CountryCodeID")}
      return(
        <countryID>{fme:get-attribute("CountryCodeValue")}</countryID>
      )
      }
    VISIBLE_QUERY_VALIDATE = Yes
    ROOT_QUERY_EXPR:
      <LCPandPRTR xmlns="http://dd.eionet.europa.eu/schemas/LCPandPRTR" xmlns:common="http://dd.eionet.europa.eu/schemas/LCPandPRTR/LCPandPRTRCommon" xmlns:xsi="http://www.w3.org/2001/XMLSchema-instance" xsi:schemaLocation="http://dd.eionet.europa.eu/schemas/LCPandPRTR http://dd.eionet.europa.eu/schemas/LCPandPRTR/LCPandPRTRMain.xsd ">
        {fme:process-features("COUNTRYID","CountryCodeID",{fme:get-attribute("countryID")})}
        <remarkText>{fme:get-attribute("remarkText")}</remarkText>
        <reportingYear>{fme:get-attribute("reportingYear")}</reportingYear>
        {fme:process-features("PLANTREPORTS","reportID",{fme:get-attribute("reportID")})}
        {fme:process-features("FACILITYREPORTS","reportID",{fme:get-attribute("reportID")})}
      </LCPandPRTR>
    OUTPUT_XML_HEADER = Yes
    FACILITYREPORTS_QUERY_EXPR:
      {
      for $valueRef in {fme:get-attribute("reportID")}
      return(
          {fme:get-xml-attribute("_FacilityReports")}
      )
      }
    PLANTREPORTS_QUERY_EXPR:
       {
      for $valueRef in {fme:get-attribute("reportID")}
      return(
          {fme:get-xml-attribute("_PlantReports")}
      )
      }
    -> StringReplacer
StringReplacer
    NO_MATCH = _FME_NO_OP_
    REGEXP = no
    SRC_ATTRS = _result
    CASE = no
    FIND_TEXT = " xmlns=\"\""
    -> XMLFormatter
XMLFormatter
    REMOVE_EMPTY_ELEMENT = Yes
    NAMESPACE_CLEANUP = No
    XML_ATTR_TEXT = _result
    INDENT_SIZE = 1
    FORMATTING_CHOICE = Pretty-Print XML
    OUTPUT_ENCODING = utf-8
    COLLAPSE_EMPTY_ELEMENT = No
    LIST_NAME = _xml_error
    XML_OUTPUT_TYPE = Attribute
    REMOVE_ALL_COMMENT = Yes
    SCHEMALOC_CLEANUP = No
    WHITESPACE_HANDLING = Remove excess whitespace
    XML_INPUT_TYPE = Attribute Specifying XML Text
    XML_OUTPUT_ATTR = _xml_output
    REPLACE_TABS_WITH_SPACES = no
    PASSED -> LCPandEPRTR (writer DATAFILE_1)
LCPandEPRTR (writer DATAFILE_1)
